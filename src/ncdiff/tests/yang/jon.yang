module jon {
  namespace "urn:jon";
  prefix jon;

  revision 2023-03-29 {
    description
      "Initial revision";
  }

  revision 2025-04-02 {
    description
      "Deprecated two nodes";
  }

  leaf foo {
    type string;
  }

  container tracking {
    leaf enabled {
      type boolean;
      default "false"; /* Deprecated, use 'enabled-v2' instead */
      status deprecated; /* Marked as deprecated in the 2025-04-02 revision */
    }
    leaf enabled-v2 {
      type boolean;
    }
    container logging {
      leaf local {
        type boolean;
      }
      container server {
        leaf host {
          type string;
        }
        leaf port {
          type uint16;
        }
      }
    }
  }

  list address {
    key "first last";
    ordered-by user;
    leaf last {
      type string;
      description "Last name";
    }
    leaf first {
      type string;
      description "First name";
    }
    leaf street {
      type string;
      description "Street name";
    }
    leaf city {
      type string;
      description "City name";
      default "Unknown"; /* Deprecated, use 'city-v2' instead */
      status deprecated; /* Marked as deprecated in the 2025-04-02 revision */
    }
    leaf city-v2 {
      type string;
      description "City name";
    }
  }

  leaf-list store {
    ordered-by user;
    type string;
  }

  container location {
    choice city {
      default alberta;
      case ontario {
        list ontario {
          key "name";
          leaf name {
            type string;
          }
        }
      }
      case alberta {
        list alberta {
          key "name";
          leaf name {
            type string;
          }
        }
        container other-info {
          leaf detail {
            type string;
            description "Additional information about Alberta.";
          }
          container geo-facts {
            leaf area {
              type int16;
              description "Area of Alberta.";
            }
            leaf population {
              type int16;
              description "Population of Alberta.";
            }
            leaf code {
              type string;
              description "Code for Alberta.";
              default "AB";
            }
          }
        }
      }
    }
  }

  container numbers {
    choice number {
      case one {
        leaf first {
          type string;
        }
      }
      case two {
        leaf second {
          type string;
        }
        leaf third {
          type string;
        }
      }
    }
  }

  container errdisable {
    description
      "Error disable";
    container detect {
      description
        "Error disable detection";
      container cause-config {
        description
          "Enable error disable detection for application";
        leaf sfp-config-mismatch {
          description
            "Enable error detection on SFP config mismatch";
          type boolean;
          default "true";
        }
        leaf small-frame {
          description
            "Enable error detection on small_frame";
          type boolean;
          default "true";
        }
        leaf loopdetect {
          description
            "Enable error detection on loop detect";
          type boolean;
          default "true";
        }
        leaf-list leaflist1 {
          description
            "Enable error detection on leaflist1";
          type string;
          ordered-by user;
          default "abc";
          default "def";
          default "ghi";
        }
        leaf-list leaflist2 {
          description
            "Enable error detection on leaflist2";
          type string;
          default "abc";
          default "def";
          default "ghi";
        }
      }
    }
  }
}
