module Cisco-IOS-XE-ospf-oper {
  yang-version 1;
  namespace "http://cisco.com/ns/yang/Cisco-IOS-XE-ospf-oper";
  prefix ospf-ios-xe-oper;

  import ietf-inet-types {
    prefix inet;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions for
     monitoring the operation of ospf protocol in a Network Element.
     Copyright (c) 2016-2017 by Cisco Systems, Inc.
     All rights reserved.";

  revision 2017-10-10 {
    description
      "Initial revision";
    reference "1.0.0";
  }

  typedef address-family {
    type enumeration {
      enum "address-family-ipv4" {
        value 0;
      }
      enum "address-family-ipv6" {
        value 1;
      }
    }
    description
      "Address family type";
  }

  typedef ospf-operation-mode {
    type enumeration {
      enum "ospf-ships-in-the-night" {
        value 0;
        description
          "Ships-in-the-night operation mode in which each OSPF instance carries only one address family";
      }
    }
    description
      "OSPF operational mode";
  }

  typedef ospf-network-type {
    type enumeration {
      enum "ospf-broadcast" {
        value 0;
        description
          "OSPF broadcast multi-access network";
      }
      enum "ospf-non-broadcast" {
        value 1;
        description
          "OSPF Non-Broadcast Multi-Access (NBMA) network";
      }
      enum "ospf-point-to-multipoint" {
        value 2;
        description
          "OSPF point-to-multipoint network";
      }
      enum "ospf-point-to-point" {
        value 3;
        description
          "OSPF point-to-point network";
      }
    }
    description
      "OSPF network type";
  }

  typedef ospf-auth-type {
    type enumeration {
      enum "ospf-auth-ipsec" {
        value 0;
      }
      enum "ospf-auth-trailer-keychain" {
        value 1;
      }
      enum "ospf-auth-trailer-key" {
        value 2;
      }
      enum "ospf-auth-type-none" {
        value 3;
      }
    }
    description
      "OSPF Authentication type";
  }

  typedef nbr-state-type {
    type enumeration {
      enum "ospf-nbr-down" {
        value 1;
        description
          "Neighbor state down";
      }
      enum "ospf-nbr-attempt" {
        value 2;
        description
          "Neighbor attempt state";
      }
      enum "ospf-nbr-init" {
        value 3;
        description
          "Neighbor init state";
      }
      enum "ospf-nbr-two-way" {
        value 4;
        description
          "Neighbor 2-way state";
      }
      enum "ospf-nbr-exchange-start" {
        value 5;
        description
          "Neighbor exchange start state";
      }
      enum "ospf-nbr-exchange" {
        value 6;
        description
          "Neighbor exchange state";
      }
      enum "ospf-nbr-loading" {
        value 7;
        description
          "Neighbor loading state";
      }
      enum "ospf-nbr-full" {
        value 8;
        description
          "Neighbor full state";
      }
    }
    description
      "OSPF neighbor state type";
  }

  typedef lsa-flag-options {
    type bits {
      bit LSA_FLAG_OPTIONS_DC {
        position 0;
      }
      bit LSA_FLAG_OPTIONS_P {
        position 1;
      }
      bit LSA_FLAG_OPTIONS_MC {
        position 2;
      }
      bit LSA_FLAG_OPTIONS_E {
        position 3;
      }
      bit LSA_FLAG_OPTIONS_UPWARD {
        position 4;
      }
      bit LSA_FLAG_OPTIONS_MT {
        position 5;
      }
      bit LSA_FLAG_OPTIONS_R {
        position 6;
      }
      bit LSA_FLAG_OPTIONS_AF {
        position 7;
      }
    }
    description
      "LSA options";
  }

  typedef ospfv2-lsa-body-flags-options {
    type bits {
      bit OSPV2_LSA_BODY_FLAG_OPTIONS_V {
        position 0;
      }
      bit OSPV2_LSA_BODY_FLAG_OPTIONS_E {
        position 1;
      }
      bit OSPV2_LSA_BODY_FLAG_OPTIONS_B {
        position 2;
      }
    }
    description
      "OSPFv2 LSA body flags";
  }

  typedef ospfv3-lsa-options {
    type bits {
      bit OSPFV3_LSA_FLAG_DC {
        position 0;
      }
      bit OSPFV3_LSA_FLAG_R {
        position 1;
      }
      bit OSPFV3_LSA_FLAG_N {
        position 2;
      }
      bit OSPFV3_LSA_FLAG_E {
        position 3;
      }
      bit OSPFV3_LSA_FLAG_V6 {
        position 4;
      }
      bit OSPFV3_LSA_FLAG_AF {
        position 5;
      }
    }
    description
      "The flags associated with the OSPFv3 LSA";
  }

  typedef ospfv3-lsa-body-flag-options {
    type bits {
      bit OSPFV3_LSA_BODY_FLAG_OPTIONS_V {
        position 0;
      }
      bit OSPFV3_LSA_BODY_FLAG_OPTIONS_E {
        position 1;
      }
      bit OSPFV3_LSA_BODY_FLAG_OPTIONS_B {
        position 2;
      }
      bit OSPFV3_LSA_BODY_FLAG_OPTIONS_NT {
        position 3;
      }
    }
    description
      "OSPFv3 LSA body flags";
  }

  grouping ospfv2-unknown-sub-tlv {
    description
      "OSPF V2 unknown Sub TLV";
    leaf type {
      type uint16;
      description
        "TLV type";
    }
    leaf length {
      type uint16;
      description
        "TLV length";
    }
    leaf-list value {
      type uint8;
      ordered-by user;
      description
        "TLV value";
    }
  }

  grouping ospfv2-link-tlv {
    description
      "OSPF V2 Link TLV";
    leaf link-type {
      type uint8;
      description
        "Link type";
    }
    leaf link-id {
      type uint32;
      description
        "Link ID";
    }
    leaf-list local-if-ipv4-addr {
      type inet:ip-address;
      ordered-by user;
      description
        "List of local interface IPv4 addresses";
    }
    leaf-list local-remote-ipv4-addr {
      type inet:ip-address;
      ordered-by user;
      description
        "List of remote interface IPv4 addresses";
    }
    leaf te-metric {
      type uint32;
      description
        "TE metric";
    }
    leaf max-bandwidth {
      type decimal64 {
        fraction-digits 2;
      }
      description
        "Maximum bandwidth";
    }
    leaf max-reservable-bandwidth {
      type decimal64 {
        fraction-digits 2;
      }
      description
        "Maximum reservable bandwidth";
    }
    leaf unreserved-bandwidth {
      type decimal64 {
        fraction-digits 2;
      }
      description
        "Unrseerved bandwidth";
    }
    leaf admin-group {
      type uint32;
      description
        "Administrative group/Resource class/Color";
    }
  }

  grouping ospfv2-unknown-tlv {
    description
      "OSPFv2 unknown type TLV";
    leaf type {
      type uint16;
      description
        "TLV type";
    }
    leaf length {
      type uint16;
      description
        "TLV length";
    }
    leaf-list value {
      type uint8;
      ordered-by user;
      description
        "TLV value";
    }
  }

  grouping ospfv2-external {
    description
      "external LSA";
    leaf mt-id {
      type uint32;
      description
        "MT-ID for topology enabled on the link";
    }
    leaf metric {
      type uint32;
      description
        "Metric for the topology";
    }
    leaf forwarding-address {
      type inet:ip-address;
      description
        "Forwarding address";
    }
    leaf external-route-tag {
      type uint32;
      description
        "Route tag";
    }
  }

  grouping ospfv2-topology {
    description
      "OSPFv2 topology";
    leaf mt-id {
      type uint32;
      description
        "MT-ID for topology enabled link";
    }
    leaf metric {
      type uint16;
      description
        "Metric for the topology";
    }
  }

  grouping ospfv2-link-key {
    description
      "OSPFv2 link key";
    leaf link-id {
      type uint32;
      description
        "Link ID";
    }
    leaf link-data {
      type uint32;
      description
        "Link data";
    }
  }

  grouping ospfv2-link {
    description
      "OSPFv2 link";
    leaf type {
      type uint8;
      description
        "Link type";
    }
    list ospfv2-topology {
      key "mt-id";
      description
        "Topology specific information";
      uses ospf-ios-xe-oper:ospfv2-topology;
    }
  }

  grouping link-scope-lsa-key {
    description
      "Link scope LSA key";
    leaf lsa-id {
      type uint32;
      description
        "LSA ID";
    }
    leaf adv-router {
      type inet:ip-address;
      description
        "Advertising router";
    }
  }

  grouping ospfv2-network {
    description
      "OSPFv2 network info";
    leaf network-mask {
      type inet:ip-address;
      description
        "IP network mask";
    }
    leaf-list attached-router {
      type uint32;
      ordered-by user;
      description
        "List of the routers attached to the network";
    }
  }

  grouping ospfv2-lsa-body {
    description
      "OSPFv2 LSA body";
    leaf num-of-links {
      type uint16;
      description
        "Number of links";
    }
    container network {
      description
        "Network details";
      uses ospf-ios-xe-oper:ospfv2-network;
    }
    leaf summary-mask {
      type inet:ip-address;
      description
        "Summary mask";
    }
    leaf external-mask {
      type inet:ip-address;
      description
        "External mask";
    }
    leaf body-flag-options {
      type ospf-ios-xe-oper:ospfv2-lsa-body-flags-options;
      description
        "LSA body flags";
    }
  }

  grouping lsa-header {
    description
      "LSA header";
    leaf age {
      type uint16;
      description
        "LSA age";
    }
    leaf type {
      type uint16;
      description
        "LSA type";
    }
    leaf adv-router {
      type uint32;
      description
        "LSA advertising router";
    }
    leaf seq-num {
      type string;
      description
        "LSA sequence number";
    }
    leaf checksum {
      type string;
      description
        "LSA checksum";
    }
    leaf length {
      type uint16;
      description
        "LSA length";
    }
  }

  grouping ospfv2-header {
    description
      "OSPFv2 header";
    leaf lsa-id {
      type inet:ip-address;
      description
        "LSA ID";
    }
    leaf opaque-type {
      type uint8;
      description
        "Opaque type";
    }
    leaf opaque-id {
      type uint32;
      description
        "Opaque ID";
    }
    leaf age {
      type uint16;
      description
        "LSA age";
    }
    leaf type {
      type uint16;
      description
        "LSA type";
    }
    leaf adv-router {
      type uint32;
      description
        "LSA advertising router";
    }
    leaf seq-num {
      type string;
      description
        "LSA sequence number";
    }
    leaf checksum {
      type string;
      description
        "LSA checksum";
    }
    leaf length {
      type uint16;
      description
        "LSA length";
    }
    leaf flag-options {
      type ospf-ios-xe-oper:lsa-flag-options;
      description
        "LSA options";
    }
  }

  grouping ospfv2-lsa {
    description
      "OSPFv2 LSA";
    container header {
      description
        "Decoded OSPFv2 LSA header data";
      uses ospf-ios-xe-oper:ospfv2-header;
    }
    container lsa-body {
      description
        "Decoded OSPFv2 LSA body data";
      uses ospf-ios-xe-oper:ospfv2-lsa-body;
    }
  }

  grouping ospfv3-header {
    description
      "OSPFv3 header";
    leaf lsa-id {
      type inet:ip-address;
      description
        "LSA ID";
    }
    container lsa-header {
      description
        "LSA header";
      uses ospf-ios-xe-oper:lsa-header;
    }
    leaf lsa-hdr-options {
      type ospf-ios-xe-oper:ospfv3-lsa-options;
      description
        "OSPFv3 LSA options";
    }
  }

  grouping ospfv3-network {
    description
      "OSPFv3 network LSA";
    leaf-list attached-router {
      type uint32;
      ordered-by user;
      description
        "List of the routers attached to the network";
    }
    leaf lsa-net-options {
      type ospf-ios-xe-oper:ospfv3-lsa-options;
      description
        "Network LSA options";
    }
  }

  grouping ospfv3-inter-area-prefix {
    description
      "OSPFv3 inter area router LSA";
    leaf metric {
      type uint32;
      description
        "Metric";
    }
    leaf ia-prefix {
      type string;
      description
        "Inter area Prefix";
    }
    leaf ia-prefix-options {
      type string;
      description
        "Inter area prefix options";
    }
  }

  grouping ospfv3-inter-area-router {
    description
      "OSPFv3 inter area router info";
    leaf metric {
      type uint32;
      description
        "Metric";
    }
    leaf destination-router-id {
      type uint32;
      description
        "Router ID of the router being described by the LSA";
    }
    leaf lsa-ia-options {
      type ospf-ios-xe-oper:ospfv3-lsa-options;
      description
        "Inter area LSA options";
    }
  }

  grouping ospfv3-lsa-external-flags {
    description
      "OSPFv3 LSA external flags";
    leaf e-flag {
      type boolean;
      description
        "When set, the metric specified is a Type 2 external metric";
    }
  }

  grouping ospfv3-lsa-external {
    description
      "OSPFv3 AS-External and NSSA LSA";
    leaf metric {
      type uint32;
      description
        "Metric";
    }
    container flags {
      description
        "LSA Flags";
      uses ospf-ios-xe-oper:ospfv3-lsa-external-flags;
    }
    leaf referenced-ls-type {
      type uint16;
      description
        "Referenced Link State type";
    }
    leaf external-prefix {
      type string;
      description
        "Prefix";
    }
    leaf external-prefix-options {
      type string;
      description
        "Prefix options";
    }
    leaf forwarding-address {
      type inet:ip-address;
      description
        "Forwarding address";
    }
    leaf external-route-tag {
      type uint32;
      description
        "Route tag";
    }
    leaf referenced-link-state-id {
      type uint32;
      description
        "Referenced Link State ID";
    }
  }

  grouping ospfv3-nssa {
    description
      "OSPFv3 NSSA LSA";
    container lsa-nssa-external {
      description
        "NSSA LSA";
      uses ospf-ios-xe-oper:ospfv3-lsa-external;
    }
  }

  grouping ospfv3-link-data {
    description
      "OSPFv3 Link Datat";
    leaf rtr-priority {
      type uint8;
      description
        "Router priority of the interce";
    }
    leaf link-local-interface-address {
      type inet:ip-address;
      description
        "The originating router's link-local interface address on the link";
    }
    leaf num-of-prefixes {
      type uint32;
      description
        "Number of prefixes";
    }
    leaf lsa-id-options {
      type ospf-ios-xe-oper:ospfv3-lsa-options;
      description
        "Link data LSA options";
    }
  }

  grouping ospfv3-intra-area-prefix {
    description
      "OSPFv3 intra area prefix LSA";
    leaf referenced-ls-type {
      type uint16;
      description
        "Referenced Link State type";
    }
    leaf referenced-link-state-id {
      type uint32;
      description
        "Referenced Link State ID";
    }
    leaf referenced-adv-router {
      type inet:ip-address;
      description
        "Referenced Advertising Router";
    }
    leaf num-of-prefixes {
      type uint16;
      description
        "Number of prefixes";
    }
  }

  grouping ospfv3-lsa-body {
    description
      "Decoded OSPFv3 LSA body data";
    container network {
      description
        "OSPFv3 network";
      uses ospf-ios-xe-oper:ospfv3-network;
    }
    container prefix {
      description
        "OSPFv3 inter area prefix";
      uses ospf-ios-xe-oper:ospfv3-inter-area-prefix;
    }
    container ia-router {
      description
        "OSPFv3 inter area router";
      uses ospf-ios-xe-oper:ospfv3-inter-area-router;
    }
    container lsa-external {
      description
        "OSPFv3 LSA external";
      uses ospf-ios-xe-oper:ospfv3-lsa-external;
    }
    container nssa {
      description
        "OSPFv3 NSSA";
      uses ospf-ios-xe-oper:ospfv3-nssa;
    }
    container link-data {
      description
        "OSPFv3 Link data";
      uses ospf-ios-xe-oper:ospfv3-link-data;
    }
    container ia-prefix {
      description
        "OSPFv3 Intra area prefixes";
      uses ospf-ios-xe-oper:ospfv3-intra-area-prefix;
    }
    leaf lsa-flag-options {
      type ospf-ios-xe-oper:ospfv3-lsa-options;
      description
        "LSA options";
    }
    leaf lsa-body-flags {
      type ospf-ios-xe-oper:ospfv3-lsa-body-flag-options;
      description
        "LSA Body Flags";
    }
  }

  grouping ospfv3-lsa {
    description
      "OSPFv3 LSA";
    container header {
      description
        "Decoded OSPFv3 LSA header";
      uses ospf-ios-xe-oper:ospfv3-header;
    }
    container lsa-body {
      description
        "Decoded OSPFv3 LSA body";
      uses ospf-ios-xe-oper:ospfv3-lsa-body;
    }
  }

  grouping ospfv3-link-key {
    description
      "OSPFv3 link key";
    leaf interface-id {
      type uint32;
      description
        "Interface ID";
    }
    leaf neighbor-interface-id {
      type uint32;
      description
        "Neighbor interface ID";
    }
    leaf neighbor-router-id {
      type uint32;
      description
        "Neighbor router ID";
    }
  }

  grouping ospfv3-link {
    description
      "OSPFv3 link";
    leaf type {
      type uint8;
      description
        "Link type";
    }
    leaf metric {
      type uint16;
      description
        "Metric";
    }
  }

  grouping ospfv3-prefix-list {
    description
      "OSPFv3 prefix list";
    leaf prefix {
      type string;
      description
        "Prefix";
    }
    leaf prefix-options {
      type string;
      description
        "Prefix options";
    }
  }

  grouping multi-topology {
    description
      "Multi topology";
    leaf name {
      type string;
      description
        "One of the topology enabled on this interface";
    }
  }

  grouping link-scope-lsa {
    description
      "Link scope LSA";
    leaf decoded-completed {
      type boolean;
      description
        "The OSPF LSA body is fully decoded";
    }
    leaf-list raw-data {
      type uint8;
      ordered-by user;
      description
        "The complete LSA in network byte order as received/sent over the wire";
    }
    leaf version {
      type uint32;
      description
        "Version";
    }
    container ospfv2-lsa {
      description
        "OSPFv2 LSA";
      uses ospf-ios-xe-oper:ospfv2-lsa;
    }
    list ospfv2-link {
      key "link-id link-data";
      description
        "OSPFv2 LSA link";
      uses ospf-ios-xe-oper:ospfv2-link-key;
      uses ospf-ios-xe-oper:ospfv2-link;
    }
    list ospfv2-topology {
      key "mt-id";
      description
        "Summary LSA";
      uses ospf-ios-xe-oper:ospfv2-topology;
    }
    list ospfv2-external {
      key "mt-id";
      description
        "External LSA";
      uses ospf-ios-xe-oper:ospfv2-external;
    }
    list ospfv2-unknown-tlv {
      key "type";
      description
        "OSPFv2 Unknown TLV";
      uses ospf-ios-xe-oper:ospfv2-unknown-tlv;
    }
    container ospfv3-lsa-val {
      description
        "OSPFv3 LSA";
      uses ospf-ios-xe-oper:ospfv3-lsa;
    }
    list ospfv3-link {
      key "interface-id neighbor-interface-id neighbor-router-id";
      description
        "OSPFv3 links";
      uses ospf-ios-xe-oper:ospfv3-link-key;
      uses ospf-ios-xe-oper:ospfv3-link;
    }
    list tbl-ospfv3-prefix-list {
      key "prefix";
      description
        "OSPFv3 prefix-list";
      uses ospf-ios-xe-oper:ospfv3-prefix-list;
    }
    list ospfv3-ia-prefix {
      key "prefix";
      description
        "OSPFv3 intra-area prefix-list";
      uses ospf-ios-xe-oper:ospfv3-prefix-list;
    }
    list multi-topology {
      key "name";
      description
        "OSPF multi-topology interface augmentation";
      uses ospf-ios-xe-oper:multi-topology;
    }
    leaf router-address {
      type inet:ip-address;
      description
        "Router address";
    }
    container tlv {
      description
        "Link TLV";
      uses ospf-ios-xe-oper:ospfv2-link-tlv;
    }
    list unknown-sub-tlv {
      key "type";
      description
        "OSPFv2 Unknown sub TLV";
      uses ospf-ios-xe-oper:ospfv2-unknown-sub-tlv;
    }
  }

  grouping area-scope-lsa-key {
    description
      "OSPF area scope LSA key";
    leaf lsa-type {
      type uint32;
      description
        "LSA Type";
    }
    leaf adv-router {
      type inet:ip-address;
      description
        "Advertising router";
    }
  }

  grouping area-scope-lsa {
    description
      "OSPF area scope LSA";
    leaf decoded-completed {
      type boolean;
      description
        "The OSPF LSA body is fully decoded";
    }
    leaf-list raw-data {
      type uint8;
      ordered-by user;
      description
        "The complete LSA in network byte order as received/sent over the wire";
    }
    container ospfv2-lsa {
      description
        "OSPFv2 LSA";
      uses ospf-ios-xe-oper:ospfv2-lsa;
    }
    list ospfv2-link {
      key "link-id link-data";
      description
        "Router LSA link";
      uses ospf-ios-xe-oper:ospfv2-link-key;
      uses ospf-ios-xe-oper:ospfv2-link;
    }
    list ospfv2-topology {
      key "mt-id";
      description
        "Summary LSA";
      uses ospf-ios-xe-oper:ospfv2-topology;
    }
    list ospfv2-external {
      key "mt-id";
      description
        "External LSA";
      uses ospf-ios-xe-oper:ospfv2-external;
    }
    container ospfv3-lsa {
      description
        "OSPFv3 LSA";
      uses ospf-ios-xe-oper:ospfv3-lsa;
    }
    list ospfv3-link {
      key "interface-id neighbor-interface-id neighbor-router-id";
      description
        "OSPFv3 links";
      uses ospf-ios-xe-oper:ospfv3-link-key;
      uses ospf-ios-xe-oper:ospfv3-link;
    }
    list ospfv3-prefix {
      key "prefix";
      description
        "OSPFv3 prefix-list";
      uses ospf-ios-xe-oper:ospfv3-prefix-list;
    }
    list ospfv3-ia-prefix {
      key "prefix";
      description
        "OSPFv3 intra-area prefix-list";
      uses ospf-ios-xe-oper:ospfv3-prefix-list;
    }
  }

  grouping area-scope-lsas {
    description
      "OSPF area scope LSA";
    leaf lsa-type {
      type uint32;
      description
        "OSPF link scope LSA type";
    }
    list area-scope-lsa {
      key "lsa-type adv-router";
      description
        "List of OSPF link scope LSAs";
      uses ospf-ios-xe-oper:area-scope-lsa-key;
      uses ospf-ios-xe-oper:area-scope-lsa;
    }
  }

  grouping link-scope-lsas {
    description
      "Link scope lsas";
    leaf lsa-type {
      type uint32;
      description
        "OSPF link scope LSA type";
    }
    list link-scope-lsa {
      key "lsa-id adv-router";
      description
        "List of OSPF link scope LSAs";
      uses ospf-ios-xe-oper:link-scope-lsa-key;
      uses ospf-ios-xe-oper:link-scope-lsa;
    }
    list area-scope-lsa {
      key "lsa-type adv-router";
      description
        "List OSPF area scope LSA databases";
      uses ospf-ios-xe-oper:area-scope-lsa-key;
      uses ospf-ios-xe-oper:area-scope-lsa;
    }
  }

  grouping ospf-static-neighbor {
    description
      "OSPF neighbor info";
    leaf address {
      type inet:ip-address;
      description
        "Neighbor IP address";
    }
    leaf cost {
      type uint16;
      description
        "Neighbor cost";
    }
    leaf poll-interval {
      type uint16;
      units "seconds";
      description
        "Neighbor polling intervali in seconds";
    }
  }

  grouping ospf-nbr-stat {
    description
      "OSPF neighbor statistics";
    leaf nbr-event-count {
      type uint32;
      description
        "The number of time this neighbor has changed state or an error has occurred";
    }
    leaf nbr-retrans-qlen {
      type uint32;
      description
        "The current length of the retransmission queue";
    }
  }

  grouping ospf-neighbor {
    description
      "OSPF neighbor details";
    leaf neighbor-id {
      type inet:ip-address;
      description
        "OSPF neighbor ID";
    }
    leaf address {
      type inet:ip-address;
      description
        "Neighbor address";
    }
    leaf dr {
      type inet:ip-address;
      description
        "Designated Router";
    }
    leaf bdr {
      type inet:ip-address;
      description
        "Backup Designated Router";
    }
    leaf state {
      type ospf-ios-xe-oper:nbr-state-type;
      description
        "OSPF neighbor state";
    }
    container stats {
      description
        "Per-neighbor statistics";
      uses ospf-ios-xe-oper:ospf-nbr-stat;
    }
  }

  grouping fast-reroute {
    description
      "Fast Reroute details";
    leaf candidate-disabled {
      type boolean;
      description
        "Prevent the interface to be used as backup";
    }
    leaf enabled {
      type boolean;
      description
        "Activates LFA. This model assumes activation of per-prefix LFA";
    }
    leaf remote-lfa-enabled {
      type boolean;
      description
        "Activates remote LFA";
    }
  }

  grouping multi-area {
    description
      "Multi Area info";
    leaf multi-area-id {
      type uint32;
      description
        "Multi-area ID";
    }
    leaf cost {
      type uint16;
      description
        "Interface cost for multi-area";
    }
  }

  grouping ospf-crypto-algorithm {
    description
      "Crypto Algorithm";
    leaf hmac-sha1-12 {
      type empty;
      description
        "HMAC-SHA1-12 algorithm";
    }
    leaf hmac-sha1-20 {
      type empty;
      description
        "HMAC-SHA1-20 algorithm";
    }
    leaf md5 {
      type empty;
      description
        "MD5 algorithm";
    }
    leaf sha-1 {
      type empty;
      description
        "SHA-1 algorithm";
    }
    leaf hmac-sha-1 {
      type empty;
      description
        "HMAC-SHA-1 authentication algorithm";
    }
    leaf hmac-sha-256 {
      type empty;
      description
        "HMAC-SHA-256 authentication algorithm";
    }
    leaf hmac-sha-384 {
      type empty;
      description
        "HMAC-SHA-384 authentication algorithm";
    }
    leaf hmac-sha-512 {
      type empty;
      description
        "HMAC-SHA-512 authentication algorithm";
    }
  }

  grouping ospf-authentication {
    description
      "OSPF authentication info";
    choice auth-type-selection-choice {
      description
        "OSPF authentication type";
      case ospf-auth-ipsec {
        leaf sa {
          type string;
          description
            "SA name";
        }
      }
      case ospf-auth-trailer-keychain {
        leaf key-chain {
          type string;
          description
            "key-chain name";
        }
      }
      case ospf-auth-trailer-key {
        leaf key-string {
          type string;
          description
            "Key string in ASCII format";
        }
        container crypto-algorithm-val {
          description
            "Crypto algorithm";
          uses ospf-ios-xe-oper:ospf-crypto-algorithm;
        }
      }
      case ospf-auth-type-none {
        leaf no-auth {
          type uint32;
          description
            "No authentication enabled";
        }
      }
    }
  }

  grouping ttl-security {
    description
      "TTL security check";
    leaf enabled {
      type boolean;
      description
        "Enable/Disable TTL security check";
    }
    leaf hops {
      type uint8;
      description
        "Maximum number of hops that a OSPF packet may have traveled";
    }
  }

  grouping ospf-interface {
    description
      "OSPF interface";
    leaf name {
      type string;
      description
        "Interface name";
    }
    leaf network-type {
      type ospf-ios-xe-oper:ospf-network-type;
      description
        "Network type";
    }
    leaf passive {
      type boolean;
      description
        "Enable/Disable passive";
    }
    leaf demand-circuit {
      type boolean;
      description
        "Enable/Disable demand circuit";
    }
    container multi-area {
      description
        "Multi Area";
      uses ospf-ios-xe-oper:multi-area;
    }
    list static-neighbor {
      key "address";
      description
        "Staticly configured neighbors";
      uses ospf-ios-xe-oper:ospf-static-neighbor;
    }
    leaf node-flag {
      type boolean;
      description
        "Set prefix as a node representative prefix";
    }
    container fast-reroute {
      description
        "Fast reroute config";
      uses ospf-ios-xe-oper:fast-reroute;
    }
    leaf cost {
      type uint16;
      description
        "Interface cost";
    }
    leaf hello-interval {
      type uint16;
      description
        "Time between hello packets";
    }
    leaf dead-interval {
      type uint16;
      description
        "Interval after which a neighbor is declared dead";
    }
    leaf retransmit-interval {
      type uint16;
      description
        "Time between retransmitting unacknowledged Link State Advertisements (LSAs)";
    }
    leaf transmit-delay {
      type uint16;
      description
        "Estimated time needed to send link-state update";
    }
    leaf mtu-ignore {
      type boolean;
      description
        "Enable/Disable ignoring of MTU in DBD packets";
    }
    leaf lls {
      type boolean;
      description
        "Enable/Disable link-local signaling (LLS) support";
    }
    leaf prefix-suppression {
      type boolean;
      description
        "Suppress advertisement of the prefixes";
    }
    leaf bfd {
      type boolean;
      description
        "Enable/disable bfd";
    }
    container ttl-security {
      description
        "TTL security";
      uses ospf-ios-xe-oper:ttl-security;
    }
    leaf enable {
      type boolean;
      description
        "Enable/disable protocol on the interface";
    }
    container authentication {
      description
        "Authentication configuration";
      uses ospf-ios-xe-oper:ospf-authentication;
    }
    leaf state {
      type string;
      description
        "Interface state";
    }
    leaf hello-timer {
      type uint32;
      description
        "Hello timer";
    }
    leaf wait-timer {
      type uint32;
      description
        "Wait timer";
    }
    leaf dr {
      type inet:ip-address;
      description
        "Designated Router";
    }
    leaf bdr {
      type inet:ip-address;
      description
        "Backup Designated Router";
    }
    list ospf-neighbor {
      key "neighbor-id";
      description
        "List of OSPF neighbors";
      uses ospf-ios-xe-oper:ospf-neighbor;
    }
    list intf-link-scope-lsas {
      key "lsa-type";
      description
        "List OSPF link scope LSAs";
      uses ospf-ios-xe-oper:link-scope-lsas;
    }
    list intf-multi-topology {
      key "name";
      description
        "OSPF interface topology";
      uses ospf-ios-xe-oper:multi-topology;
    }
    leaf priority {
      type uint8;
      description
        "Configure OSPF router priority";
    }
  }

  grouping ospf-area {
    description
      "OSPF area";
    leaf area-id {
      type uint32;
      description
        "OSPF area ID";
    }
    list ospf-interface {
      key "name";
      description
        "List of OSPF interfaces";
      uses ospf-ios-xe-oper:ospf-interface;
    }
    list area-scope-lsa {
      key "lsa-type";
      description
        "List of OSPF area scope LSA";
      uses ospf-ios-xe-oper:area-scope-lsas;
    }
  }

  grouping ospf-instance-rev1-key {
    description
      "OSPF instance key type";
    leaf af {
      type ospf-ios-xe-oper:address-family;
      description
        "Address-family of the instance";
    }
    leaf router-id {
      type uint32;
      description
        "Defined in RFC 2328. A 32-bit number that uniquely identifies the router";
    }
  }

  grouping ospf-instance-rev1 {
    description
      "OSPF instance";
    list ospf-area {
      key "area-id";
      description
        "List of ospf areas";
      uses ospf-ios-xe-oper:ospf-area;
    }
    list link-scope-lsas {
      key "lsa-type";
      description
        "List OSPF link scope LSA";
      uses ospf-ios-xe-oper:link-scope-lsas;
    }
    list multi-topology {
      key "name";
      description
        "OSPF multi-topology interface augmentation";
      uses ospf-ios-xe-oper:multi-topology;
    }
  }

  grouping ospf-rev1 {
    description
      "OSPF operational data";
    leaf op-mode {
      type ospf-ios-xe-oper:ospf-operation-mode;
      description
        "OSPF operation mode";
    }
    list ospf-instance {
      key "af router-id";
      description
        "OSPF routing protocol instance";
      uses ospf-ios-xe-oper:ospf-instance-rev1-key;
      uses ospf-ios-xe-oper:ospf-instance-rev1;
    }
  }

  container ospf-oper-data {
    config false;
    description
      "Operational state of ospf";
    container ospf-state {
      presence "tbl-ospf";
      description
        "OSPF operational state";
      uses ospf-ios-xe-oper:ospf-rev1;
    }
  }
}
