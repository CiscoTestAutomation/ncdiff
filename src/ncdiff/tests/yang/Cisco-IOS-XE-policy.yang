module Cisco-IOS-XE-policy {
  namespace "http://cisco.com/ns/yang/Cisco-IOS-XE-policy";
  prefix ios-policy;

  import ietf-inet-types {
    prefix inet;
  }

  import ietf-yang-types {
    prefix yang;
  }

  import Cisco-IOS-XE-types {
    prefix ios-types;
  }

  import Cisco-IOS-XE-features {
    prefix ios-features;
  }

  import Cisco-IOS-XE-native {
    prefix ios;
  }


  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Policy Map Yang Model.
     Copyright (c) 2016-2017 by Cisco Systems, Inc.
     All rights reserved.";

  // =========================================================================
  // REVISION
  // =========================================================================
  revision 2017-11-27 {
     description
       "Added Change 25GE name";
  }

  revision 2017-11-14 {
    description
      "This revision has changes for new 100GE interface addition";
  }

  revision 2017-09-15 {
    description
      "This revision has changes for new 2gig interface addition";
  }
  revision 2017-09-01 {
    description
     "Add dependency for random-detect cos";
  }
  revision 2017-08-26 {
    description
     "Add parameter-map regex";
  }
  revision 2017-08-24 {
    description
     "Add sequence optional for random-detect precedence";
  }
  revision 2017-08-16 {
    description
      "This revision has changes for new 5gig and 25gig interfaces addition";
  }
  revision 2017-07-31 {
    description
     "Changes to match protocol and attribute";
  }
  revision 2017-07-21 {
    description
     "add class-map match service";
  }
  revision 2017-07-16 {
    description
     "add random-detect cos options";
  }
  revision 2017-07-13 {
    description 
     "Changed protocol-name as a string to support dynamically updated protocol-pack";
  }
  revision 2017-06-07 {
    description
     "add dependency match group-object security source";
  }
  revision 2017-05-08 {
    description
     "add more protocol support in match protocol";
  }
  revision 2017-03-31 {
    description
     "fix conform-action issue under policy-map";
  }
  revision 2017-03-20 {
    description
      "Add class-map match group-object";
  }
  revision 2017-02-09 {
    description
      "policy-map shape average option - account";
  }
  revision 2017-02-07 {
    description
      "Initial revision";
  }


  typedef precedence-type2 {
    type union {
      type uint8 {
        range "0..7";
      }
      type enumeration {
        enum "rsvp" {
        }
      }
    }
  }

  typedef policy-action-type {
    type enumeration {
      enum "bandwidth" {
      }
      enum "compression";
      enum "drop";
      enum "estimate";
      enum "fair-queue";
      enum "forward";
      enum "netflow-sampler";
      enum "police";
      enum "priority" {
      }
      enum "queue-limit";
      enum "random-detect";
      enum "service-policy";
      enum "set";
      enum "shape" {
      }
      enum "trust";
      enum "dbl";
      enum "queue-buffers";
    }
  }

  typedef class-name-type {
    type union {
      type string;
      // Note: leafref can't be used here due to part of union.
      //path "/ios:native/class-map/name";
      type enumeration {
        enum "class-default";
      }
    }
  }

  typedef police-packets-bytes-type {
    type enumeration {
      enum "packets";
      enum "bytes";
    }
  }

  typedef bytes-ms-us-type {
    type enumeration {
      enum "bytes";
      enum "ms";
      enum "us";
    }
  }

  typedef police-pps-bps-type {
    type enumeration {
      enum "pps";
      enum "bps";
    }
  }

  typedef police-bps-type {
    type uint64 {
      range "8000..64000000000";
    }
  }

  typedef police-burst-type {
    type uint32 {
      range "1000..512000000";
    }
  }

  // police {conform|exceed|violate}-action groupings
  grouping police-action-transmit-grouping {
    leaf transmit {
      description
        "transmit packet";
      type empty;
    }
  }

  grouping police-action-drop-grouping {
    leaf drop {
      description
        "drop packet";
      type empty;
    }
  }

  grouping police-conform-action-grouping {
    container conform-set-clp-transmit {
      container conform-action {
        description
          "action when rate is less than conform burst";
        leaf set-clp-transmit {
          description
            "set atm clp and send it";
          type empty;
        }
      }
    }
    container conform-set-cos-transmit {
      container conform-action {
        description
          "action when rate is less than conform burst";
        leaf set-cos-transmit {
          description
            "rewrite packet cos and send it";
          type ios-types:cos_value-type;
        }
      }
    }
    container conform-set-cos-transmit-table {
      container conform-action {
        description
          "action when rate is less than conform burst";
        leaf set-cos-transmit {
          description
            "rewrite packet cos and send it";
          type ios-types:cos_value-type;
        }
        leaf table {
          description
            "Specify table-map";
          type leafref {
            path "/ios:native/ios:table-map/ios:name";
          }
        }
      }
    }
    container conform-set-discard-class-transmit {
      container conform-action {
        description
          "action when rate is less than conform burst";
        leaf set-discard-class-transmit {
          description
            "set discard-class and send it";
          type uint8 {
            range "0..7";
          }
        }
      }
    }
    container conform-set-dscp-transmit {
      container conform-action {
        description
          "action when rate is less than conform burst";
        leaf set-dscp-transmit {
          description
            "set dscp and send it";
          type ios-types:dscp-type;
        }
      }
    }
    container conform-set-dscp-transmit-table {
      container conform-action {
        description
          "action when rate is less than conform burst";
        leaf set-dscp-transmit {
          description
            "set dscp and send it";
          type ios-types:dscp-type;
        }
        leaf table {
          description
            "Specify table-map";
          type leafref {
            path "/ios:native/ios:table-map/ios:name";
          }
        }
      }
    }
    container conform-set-frde-transmit {
      container conform-action {
        description
          "action when rate is less than conform burst";
        leaf set-frde-transmit {
          description
            "set FR DE and send it";
          type empty;
        }
      }
    }
    container conform-set-mpls-exp-imposition-transmit {
      container conform-action {
        description
          "action when rate is less than conform burst";
        leaf set-mpls-exp-imposition-transmit {
          description
            "set exp at tag imposition and send it";
          type ios-types:exp_value-type;
        }
      }
    }
    container conform-set-mpls-exp-imposition-transmit-table {
      container conform-action {
        description
          "action when rate is less than conform burst";
        leaf set-mpls-exp-imposition-transmit {
          description
            "set exp at tag imposition and send it";
          type ios-types:exp_value-type;
        }
        leaf table {
          description
            "Specify table-map";
          type leafref {
            path "/ios:native/ios:table-map/ios:name";
          }
        }
      }
    }
    container conform-set-mpls-exp-topmost-transmit {
      container conform-action {
        description
          "action when rate is less than conform burst";
        leaf set-mpls-exp-topmost-transmit {
          description
            "set exp on topmost label and send it";
          type ios-types:exp_value-type;
        }
      }
    }
    container conform-set-mpls-exp-topmost-transmit-table {
      container conform-action {
        description
          "action when rate is less than conform burst";
        leaf set-mpls-exp-topmost-transmit {
          description
            "set exp on topmost label and send it";
          type ios-types:exp_value-type;
        }
        leaf table {
          description
            "Specify table-map";
          type leafref {
            path "/ios:native/ios:table-map/ios:name";
          }
        }
      }
    }
    container conform-set-prec-transmit {
      container conform-action {
        description
          "action when rate is less than conform burst";
        leaf set-prec-transmit {
          description
            "rewrite packet precedence and send it";
          type ios-types:prec_value-type;
        }
      }
    }
    container conform-set-prec-transmit-table {
      container conform-action {
        description
          "action when rate is less than conform burst";
        leaf set-prec-transmit {
          description
            "rewrite packet precedence and send it";
          type ios-types:prec_value-type;
        }
        leaf table {
          description
            "Specify table-map";
          type leafref {
            path "/ios:native/ios:table-map/ios:name";
          }
        }
      }
    }
    container conform-set-qos-transmit {
      container conform-action {
        description
          "action when rate is less than conform burst";
        leaf set-qos-transmit {
          description
            "set qos-group and send it";
          type ios-types:qos_value-type;
        }
      }
    }
    container conform-set-qos-transmit-table {
      container conform-action {
        description
          "action when rate is less than conform burst";
        leaf set-qos-transmit {
          description
            "set qos-group and send it";
          type ios-types:qos_value-type;
        }
        leaf table {
          description
            "Specify table-map";
          type leafref {
            path "/ios:native/ios:table-map/ios:name";
          }
        }
      }
    }
    container conform-transmit {
      container conform-action {
        description
          "action when rate is less than conform burst";
        uses police-action-transmit-grouping;
      }
    }
    container conform-drop {
      container conform-action {
        description
          "action when rate is less than conform burst";
        uses police-action-drop-grouping;
      }
    }
  } // police-conform-action-grouping

  grouping police-exceed-action-grouping {
    container exceed-dscp {
      container exceed-action {
        description
          "action when rate is within conform and conform + exceed burst";
        leaf dscp {
          type ios-types:dscp-type;
        }
      }
    }
    container exceed-set-clp-transmit {
      container exceed-action {
        description
          "action when rate is within conform and conform + exceed burst";
        leaf set-clp-transmit {
          description
            "set atm clp and send it";
          type empty;
        }
      }
    }
    container exceed-set-cos-transmit {
      container exceed-action {
        description
          "action when rate is within conform and conform + exceed burst";
        leaf set-cos-transmit {
          description
            "rewrite packet cos and send it";
          type ios-types:cos_value-type;
        }
        leaf table {
          description
            "Specify table-map";
          type leafref {
            path "/ios:native/ios:table-map/ios:name";
          }
        }
      }
    }
    container exceed-set-discard-class-transmit {
      container exceed-action {
        description
          "action when rate is within conform and conform + exceed burst";
        leaf set-discard-class-transmit {
          description
            "set discard-class and send it";
          type uint8 {
            range "0..7";
          }
        }
      }
    }
    container exceed-set-dscp-transmit {
      container exceed-action {
        description
          "action when rate is within conform and conform + exceed burst";
        container set-dscp-transmit {
          container dscp {
            leaf table {
              type enumeration {
                enum "policed-dscp";
              }
            }
          }
        }
      }
    }
    container exceed-set-dscp-transmit-table {
      container exceed-action {
        description
          "action when rate is within conform and conform + exceed burst";
        leaf set-dscp-transmit {
          description
            "set dscp and send it";
          type ios-types:dscp-type;
        }
        leaf table {
          description
            "Specify table-map";
          type leafref {
            path "/ios:native/ios:table-map/ios:name";
          }
        }
      }
    }
    container exceed-set-frde-transmit {
      container exceed-action {
        description
          "action when rate is within conform and conform + exceed burst";
        leaf set-frde-transmit {
          description
            "set FR DE and send it";
          type empty;
        }
      }
    }
    container exceed-set-mpls-exp-imposition-transmit {
      container exceed-action {
        description
          "action when rate is within conform and conform + exceed burst";
        leaf set-mpls-exp-imposition-transmit {
          description
            "set exp at tag imposition and send it";
          type ios-types:exp_value-type;
        }
      }
    }
    container exceed-set-mpls-exp-topmost-transmit {
      container exceed-action {
        description
          "action when rate is within conform and conform + exceed burst";
        leaf set-mpls-exp-topmost-transmit {
          description
            "set exp on topmost label and send it";
          type ios-types:exp_value-type;
        }
      }
    }
    container exceed-set-prec-transmit {
      container exceed-action {
        description
          "action when rate is within conform and conform + exceed burst";
        leaf set-prec-transmit {
          description
            "rewrite packet precedence and send it";
          type ios-types:prec_value-type;
        }
        leaf table {
          description
            "Specify table-map";
          type leafref {
            path "/ios:native/ios:table-map/ios:name";
          }
        }
      }
    }
    container exceed-set-qos-transmit {
      container exceed-action {
        description
          "action when rate is within conform and conform + exceed burst";
        leaf set-qos-transmit {
          description
            "set qos-group and send it";
          type ios-types:qos_value-type;
        }
      }
    }
    container exceed-transmit {
      container exceed-action {
        description
          "action when rate is within conform and conform + exceed burst";
        uses police-action-transmit-grouping;
      }
    }
    container exceed-drop {
      container exceed-action {
        description
          "action when rate is within conform and conform + exceed burst";
        uses police-action-drop-grouping;
      }
    }
  } //police-exceed-action-grouping

  grouping police-violate-action-grouping {
    container violate-set-clp-transmit {
      container violate-action {
        description
          "action when rate is greater than conform + exceed burst";
        leaf set-clp-transmit {
          description
            "set atm clp and send it";
          type empty;
        }
      }
    }
    container violate-set-cos-transmit {
      container violate-action {
        description
          "action when rate is greater than conform + exceed burst";
        leaf set-cos-transmit {
          description
            "rewrite packet cos and send it";
          type ios-types:cos_value-type;
        }
        leaf table {
          description
            "Specify table-map";
          type leafref {
            path "/ios:native/ios:table-map/ios:name";
          }
        }
      }
    }
    container violate-set-discard-class-transmit {
      container violate-action {
        description
          "action when rate is greater than conform + exceed burst";
        leaf set-discard-class-transmit {
          description
            "set discard-class and send it";
          type uint8 {
            range "0..7";
          }
        }
      }
    }
    container violate-set-dscp-transmit {
      container violate-action {
        description
          "action when rate is greater than conform + exceed burst";
        leaf set-dscp-transmit {
          description
            "set dscp and send it";
          type ios-types:dscp-type;
        }
        leaf table {
          description
            "Specify table-map";
          type leafref {
            path "/ios:native/ios:table-map/ios:name";
          }
        }
      }
    }
    container violate-set-frde-transmit {
      container violate-action {
        description
          "action when rate is greater than conform + exceed burst";
        leaf set-frde-transmit {
          description
            "set FR DE and send it";
          type empty;
        }
      }
    }
    container violate-set-mpls-exp-imposition-transmit {
      container violate-action {
        description
          "action when rate is greater than conform + exceed burst";
        leaf set-mpls-exp-imposition-transmit {
          description
            "set exp at tag imposition and send it";
          type ios-types:exp_value-type;
        }
      }
    }
    container violate-set-mpls-exp-topmost-transmit {
      container violate-action {
        description
          "action when rate is greater than conform + exceed burst";
        leaf set-mpls-exp-topmost-transmit {
          description
            "set exp on topmost label and send it";
          type ios-types:exp_value-type;
        }
      }
    }
    container violate-set-prec-transmit {
      container violate-action {
        description
          "action when rate is greater than conform + exceed burst";
        leaf set-prec-transmit {
          description
            "rewrite packet precedence and send it";
          type ios-types:prec_value-type;
        }
        leaf table {
          description
            "Specify table-map";
          type leafref {
            path "/ios:native/ios:table-map/ios:name";
          }
        }
      }
    }
    container violate-set-qos-transmit {
      container violate-action {
        description
          "action when rate is greater than conform + exceed burst";
        leaf set-qos-transmit {
          description
            "set qos-group and send it";
          type ios-types:qos_value-type;
        }
      }
    }
    container violate-transmit {
      container violate-action {
        description
          "action when rate is greater than conform + exceed burst";
        uses police-action-transmit-grouping;
      }
    }
    container violate-drop {
      container violate-action {
        description
          "action when rate is greater than conform + exceed burst";
        uses police-action-drop-grouping;
      }
    }
  } //police-violate-action-grouping

  grouping police-action-grouping {
    container actions {
      // policy-map * / class * / police ? / conform-action
      uses police-conform-action-grouping;
      // policy-map * / class * / police ? / exceed-action
      uses police-exceed-action-grouping;
      // policy-map * / class * / police ? / violate-action
      uses police-violate-action-grouping;
    }
  }

  grouping random-detect-grouping {
    leaf min-threshold {
      description 
        "minimum threshold (in packet by default)";
      type uint32 {
        range "1..512000000";
      }
    }
    leaf min-threshold-unit {
      description
        "bytes supported on ASR platform only, ms on ASR100x only, us on ASR9xx only";
      type bytes-ms-us-type;
    }
    leaf max-threshold {
      description 
        "maximum threshold (in packet by default)";
      type uint32 {
        range "1..512000000";
      }
    }
    leaf max-threshold-unit {
      description
        "bytes supported on ASR platform only, ms on ASR100x only, us on ASR9xx only";
      type bytes-ms-us-type;
    }
    leaf denominator {
      description 
        "mark probability denominator";
      type uint16 {
        range "1..65535";
      }
    }
  }

  grouping config-policy-map-grouping {
    list policy-map {
      //Note: put the top level nodes in the base file. Nodes in
      //augmented file will show up in the submode (config-pmap)#
      description
        "Configure QoS Policy Map";
      key "name";
      leaf name {
        type string;
      }
      leaf type {
        description
          "type of the policy-map";
        type enumeration {
          enum "access-control";
          enum "appnav";
          enum "inspect";
          enum "control";
          enum "packet-service";
          enum "performance-monitor";
          enum "service";
          enum "service-chain";
        }
      }
      leaf subscriber {
        type empty;
      }
      leaf protocol {
        when "../type = 'inspect'";
        type enumeration {
          enum "http";
          enum "im";
          enum "imap";
          enum "p2p";
          enum "pop3";
          enum "smtp";
          enum "sunrpc";
        }
      }
      // policy-map * / event *
      list event {
        description
          "The event type this control class-map triggers upon";
        key "event-type";
        ordered-by user;
        leaf event-type {
          type enumeration {
            enum "aaa-available";
            enum "absolute-timeout";
            enum "agent-found";
            enum "authentication-failure";
            enum "authentication-success";
            enum "authorization-failure";
            enum "authorization-success";
            enum "identity-update";
            enum "inactivity-timeout";
            enum "remote-authentication-failure";
            enum "remote-authentication-success";
            enum "session-disconnected";
            enum "session-started";
            enum "tag-added";
            enum "tag-removed";
            enum "template-activated";
            enum "template-activation-failed";
            enum "template-deactivated";
            enum "template-deactivation-failed";
            enum "timer-expiry";
            enum "violation";
          }
        }
        leaf match-type {
          type enumeration {
            enum "match-all";
            enum "match-first";
          }
        }
        list class-number {
          description
            "class number, 1 for 1st class, 2 for 2nd...";
          key "number";
          leaf number {
            type uint8 {
              range "1..254";
            }
          }
          leaf class {
            description
              "The class type this control policy-map triggers upon";
            type union {
              type enumeration {
                enum "always";
              }
              type string;
            }
          }
          leaf execution-type {
            type enumeration {
              enum "do-all";
              enum "do-until-failure";
              enum "do-until-success";
             }
          }
          list action-number {
            description
              "action number, 1 for 1st class, 2 for 2nd...";
            key "number";
            leaf number {
              type uint8 {
                range "1..254";
              }
            }
            container terminate {
              description
                "terminate auth method";
              leaf dot1x {
                description
                  "dot1x method";
                type empty;
              }
              leaf mab {
                description
                  "mab method";
                type empty;
              }
              leaf webauth {
                description
                  "webauth method";
                type empty;
              }
            }
            leaf replace {
              description
                "clear existing session and create session for violating host";
              type empty;
            }
            leaf clear-session {
              description
                "clears an active session";
              type empty;
            }
            container resume {
              description
                "resume operation to be specified";
              leaf reauthentication {
                description
                  "resume reauthentication";
                type empty;
              }
            }
            leaf authentication-restart {
              description
                "restarts the auth sequence after the specified number of sec";
              type uint16 {
                range "1..65535";
              }
            }
            container pause {
              description
                "pause operation to be specified";
              leaf reauthentication {
                description
                  "pause reauthentication";
                type empty;
              }
            }
            leaf authorize {
              description
                "authorize session";
              type empty;
            }
            container activate  {
              description
                "activate template or policy";
              leaf service-template {
                description
                  "activate service template";
                type string;
              }
            }
            container authenticate {
              description
                "authenticate a session";
              container using {
                description
                  "authenticate a session";
                leaf method {
                  type enumeration {
                    enum "dot1x";
                    enum "mab";
                    enum "webauth";
                  }
                }
                leaf both {
                  description
                    "Enabling Dot1x Authenticator & Supplicant";
                  type empty;
                }
                leaf retries {
                  description
                    "Number of times to retry failed authentications";
                  type uint8 {
                    range "1..5";
                  }
                }
                leaf retry-time {
                  description
                    "Time interval between retries";
                  type uint16 {
                    range "0..65535";
                  }
                }
                leaf  priority {
                  description
                    "Method priority";
                  type uint8 {
                    range "1..254";
                  }
                }
                leaf parameter-map {
                  description
                    "Specify parameter map name";
                  type string; 
                }
              }
            }
            container map {
              description
                "map identity-update attribute to a auto-conf templates";
              container attribute-to-service {
                description
                  "identity-update attribute to a auto-conf templates";
                leaf table {
                  type string; 
                }
              }
            }
          }
        }
      }
      // policy-map * / class *
      list class {
        description
          "policy criteria";
        key "name";
        ordered-by user;
        leaf name {
          type class-name-type;
        }
        // policy-map * / class * / type
        leaf type {
          description
            "type of the class-map";
          type enumeration {
            enum "inspect";
          }
        }
        leaf insert-before {
          description
            "Insert the class before a specified class";
          //when "../../type = 'appnav'";
          when "../../type = 'appnav'";
          type string;
        }
        // policy-map * / class * / appnav policy
        container appnav-policy {
          when "../../type = 'appnav'";
          list distribute {
            description
              "Distribute action";
            key "service-node-group";
            leaf service-node-group {
              description
                "Distribute to service-node-group";
              type string;
            }
            leaf insert-before {
              description
                "Insert before specific node";
              type string;
            }
          }
          leaf monitor-load {
            description
              "Monitor AO";
            when "../distribute";
            type enumeration {
              enum "MS-port-mapper";
              enum "cifs";
              enum "http";
              enum "ica";
              enum "mapi";
              enum "nfs";
              enum "ssl";
              enum "video";
            }
          }
          leaf pass-through {
            description
              "pass-through action";
            type empty;
          }
        }
        // policy-map * / class * / inspect policy
        container policy {
          when "../../type = 'inspect'";
          leaf action {
            type enumeration {
              enum "cxsc";
              enum "drop";
              enum "inspect";
              enum "pass";
              enum "service-policy";
            }
          }
          leaf log {
            description
              "Send logging message for drop or pass";
            when "../action = 'drop'or ../action = 'pass'";
            type empty;
          }
          leaf parameter-map {
            when "../action = 'inspect' or ../action = 'cxsc'";
            type union {
              type string;
              type enumeration {
                enum "global";
                enum "gtp";
              }
            }
          }
          container dpi {
            when "../action = 'service-policy'";
            leaf type {
              type enumeration {
                enum "gtpv0";
                enum "gtpv1";
                enum "imap";
                enum "pop3";
                enum "smtp";
                enum "sunrpc";
              }
            }
            leaf policy-map {
              type string;
            }
          }
        }
        // policy-map * / class * / performance-monitor policy
        container pm-policy {
          when "../../type = 'performance-monitor'";
          container flow {
            description
              "Flow subcommands";
            leaf monitor {
              description
                "Apply a Flow Monitor";
              type string;
            }
          }
          container monitor {
            description
              "Monitor related parameters";
            container metric {
              description
                "Monitor metric";
              container rtp {
                description
                  "RTP metrics parameters";
                list clock-rate {
                  description
                    "RTP timestamp field's sampling frequency";
                  key "number";
                  leaf number {
                    type union {
                      type uint8 {
                        range "0..127";
                      }
                      type enumeration {
                        enum "celb";
                        enum "cn";
                        enum "default";
                        enum "dvi4";
                        enum "dvi4-2";
                        enum "dvi4-3";
                        enum "dvi4-4";
                        enum "g722";
                        enum "g723";
                        enum "g728";
                        enum "g729";
                        enum "gsm";
                        enum "h261";
                        enum "h263";
                        enum "jpeg";
                        enum "l16";
                        enum "l16-2";
                        enum "lpc";
                        enum "mp2t";
                        enum "mpa";
                        enum "mpv";
                        enum "nv";
                        enum "pcma";
                        enum "pcmu";
                        enum "qcelp";
                      }
                    }
                  }
                  leaf frequency {
                    type uint32 {
                      range "1000..192000";
                    }
                  }
                }
              }
            }
          }
          list react {
            description
              "Configure threshold crossing actions";
            key "id";
            leaf id {
              type uint16;
            }
            leaf mode {
              type enumeration {
                enum "media-stop";
                enum "mrv";
                enum "rtp-jitter-average";
                enum "transport-packets-lost-rate";
              }
            }
            leaf description {
              description
                "Description for the instance";
              type string;
            }
            container action {
              description
                "Config react action";
              leaf snmp {
                description
                  "SNMP is notified of the event";
                type empty;
              }
              leaf syslog {
                description
                  "The threshold-crossing event is logged to syslog";
                type empty;
              }
            }
            container alarm {
              description
                "Config react alarm";
              leaf severity {
                description
                  "Alarm severity - default level none";
                type enumeration {
                  enum "alert";
                  enum "critical";
                  enum "emergency";
                  enum "error";
                  enum "info";
                }
              }
              container type {
                description
                  "Alarm raised type - for each flow or a group";
                leaf discrete {
                  description
                    "Alert for each flow within the class";
                  type empty;
                }
                container grouped {
                  description
                    "Alert if more than one flow cross the threshold";
                  leaf count {
                    description
                      "Number of flows in the group cross the threshold";
                    type uint16;
                  }
                  leaf percent {
                    description
                      "Percent of flows in the group cross the threshold";
                    type uint8 {
                      range "1..100";
                    }
                  }
                }
              }
            }
            container threshold {
              description
                "Config react threshold";
              container value {
                description
                  "Range of percentage loss that would trigger the alarm";
                leaf ge {
                  description
                    "greater and equal to";
                  type string;
                }
                leaf gt {
                  description
                    "greater than";
                  type string;
                }
                leaf le {
                  description
                    "less and equal to";
                  type string;
                }
                leaf lt {
                  description
                    "less than";
                  type string;
                }
                container range {
                  description
                    "threshold within the range of";
                  leaf low {
                    type string;
                  }
                  leaf high {
                    type string;
                  }
                }
              }
            }
          }
        }
        // policy-map * / class * / inspect-police
        container inspect-police {
          when "../policy/action = 'inspect'";
          container police {
            description
              "Police";
            leaf rate {
              description
                "Specify police rate";
              type uint32 {
                range "8000..2000000000";
              }
            }
            leaf burst {
              description
                "Specify 'burst' parameter";
              type uint32 {
                range "1000..512000000";
              }
            }
          }
        }
        // Note: "random-detect" can co-exist with "random-detect precedence ..."
        // so a stand-alone model is needed.
        leaf random-detect {
          type empty;
        }
        list action-list {
          key "action-type";
          ordered-by user;
          leaf action-type {
            type policy-action-type;
          }
          choice action-param {
            // policy-map * / class * / bandwidth
            case bandwidth-case {
              container bandwidth {
                when "../action-type = 'bandwidth'";
                leaf bits {
                  type uint32 {
                    range "8..2000000";
                  }
                }
                leaf percent {
                  description 
                    "% of total Bandwidth";
                  type ios-types:percentage;
                }
                container remaining {
                  description 
                    "% of the remaining bandwidth";
                  leaf rem-option {
                    type enumeration {
                      enum "percent";
                      enum "ratio";
                    }
                  }
                  leaf percent {
                    description 
                      "% of the remaining bandwidth";
                    when "../rem-option='percent'";
                    type ios-types:percentage;
                  }
                  leaf ratio {
                    description                    
                      "ratio for sharing excess bandwidth";
		    when "../rem-option='ratio'";
                    type uint16;
                  }
                  container account {
                    description 
                      "Overhead Accounting";
                    when "../rem-option = 'percent' or ../rem-option = 'ratio'";
                    leaf user-defined {
                      description 
                        "Offset Size";
                       type int32 {
                          range "-1000000..1000000";
                       }
                    }
                  }
                }
              }
            }
            case compression-case {
              // policy-map * / class * / compression
              container compression {
                when "../action-type = 'compression'";
                container header {
                  description
                    "configure header compression";
                  presence "configure header compression";
                  leaf ip {
                    description
                      "configure ip header compression";
                    type enumeration {
                      enum "rtp" {
                      }
                      enum "tcp";
                    }
                  }
                }
              }
            }
            //case drop-case {
              // policy-map * / class * / drop
              //leaf drop {
                //type empty;
              //}
            //}
            case estimate-case {
              // policy-map * / class * / estimate
              container estimate {
                when "../action-type = 'estimate'";
                container bandwidth {
                  presence "bandwidth required to service this class";
                  description
                    "bandwidth required to service this class";
                  container delay-one-in {
                    description
                      "specify QoS target delay";
                    leaf doi {
                      type uint32 {
                        range "50..1000000";
                      }
                    }
                    leaf milliseconds {
                      type uint32 {
                        range "8..1000";
                      }
                    }
                  }
                  leaf drop-one-in {
                    description
                      "specify QoS target loss rate";
                    type uint32;
                  }
                }
              }
            }
            case forward-case {
              //policy-map * / class * / forward service-path
              container forward {
                when "../action-type = 'forward'";
                leaf service-path {
                  description
                    "Service Path Entries";
                  type uint32 {
                    range "0..16777215";
                  }
                }
                leaf service-index {
                  description
                    "Service Index";
                  type uint8 {
                    range "2..255";
                  }
                }
              }
            }
            case fair-queue-case {
              // policy-map * / class * / fair-queue
              // class-default: fair-queue [number-of-dynamic-queues]
              // DWFQ: fair-queue
              // policy-map: fair-queue [queue-limit queue-value]
              // NOT SUPPORTED:
              // air-queue [congestive-discard-threshold [dynamic-q [reservable-q]]]
              container fair-queue {
                when "../action-type = 'fair-queue'";
                leaf dynamic-queues {
                  type uint32 {
                    range "16|32|64|128|256|512|1024|2048|4096";
                  }
                }
                leaf queue-limit {
                  description
                    "per flow queue limit";
                  type uint16 {
                    range "1..32768";
                  }
                }
              }
            }
            case netflow-sampler-case {
              // policy-map * / class * / netflow-sampler
              leaf netflow-sampler {
                when "../action-type = 'netflow-sampler'";
                // should be leafref to sampler
                type string;
              }
            }
            case police-case {
              choice police-choice {
                // policy-map * / class * / police aggregate
                case police-aggregate-case {
                  container police-aggregate {
                    container police {
                      when "../../action-type = 'police'" {
                      }
                      leaf aggregate {
                        description
                          "Choose aggregate policer for current class";
                        type string;
                      }
                    }
                  }
                }
                // police (policy-map)
                // police cir <bps> [[bc <burst-normal>] [be <burst-max>]]
                //        [pir <bps> [be <burst-bytes>]] ACTIONS
                // NOTE: cir, bc & be keywords are mandatory in this model.
                //       Java code will add missing cir,bc and be in show().
                case police-policy-map-case {
                  container police-policy-map {
                    container police {
                      when "../../action-type = 'police'" {
                      }
                      leaf cir {
                        description
                          "Committed information rate";
                        type police-bps-type;
                      }
                      leaf bc {
                        description
                          "Conform burst";
                        type police-burst-type;
                      }
                      leaf be {
                        description
                          "Excess burst";
                        when "../bc";
                        type police-burst-type;
                      }
                      leaf pir {
                        description
                          "Peak Information Rate";
                        type police-bps-type;
                      }
                      container pir-be {
                        when "../pir";
                        leaf be {
                          description
                            "Excess burst";
                          type police-burst-type;
                        }
                      }
                      // conform-action | exceed-action | violate-action
                      uses police-action-grouping;
                    }
                  }
                }
                // police cir percent (combo of percent & policy-map versions)
                // police cir percent <percentage>
                //    [bc] <burst> ms] [be [<burst> ms]
                //    [pir percent <percentage> [be <burst> ms]] ACTIONS
                case police-cir-percent-case {
                  container police-cir-percent {
                    container police {
                      when "../../action-type = 'police'" {
                      }
                      container cir {
                        description
                          "Committed information rate";
                        container percent {
                          description
                            "% of interface bandwidth for Committed information rate";
                          leaf percentage {
                            type ios-types:percentage;
                          }
                          leaf bc {
                            description
                              "Conform burst";
                            type uint16;
                          }
                          container bc-ms {
                            when "../bc";
                            leaf ms {
                              description
                                "Milli seconds";
                              type empty;
                            }
                          }
                          leaf be {
                            when "../bc-ms/ms" {
                            }
                            type uint16;
                          }
                          container be-ms {
                            when "../be";
                            leaf ms {
                              description
                                "Milli seconds";
                              type empty;
                            }
                          }
                          // [pir percent <percentage> [be <burst> ms]]
                          container pir {
                            description
                              "Peak Information Rate";
                            leaf percent {
                              description
                                "% of interface bandwidth for Peak Information Rate";
                              type ios-types:percentage;
                            }
                          }
                          container pir-be {
                            when "../pir";
                            leaf be {
                              description
                                "Excess burst";
                              type uint16;
                            }
                          }
                          container pir-be-ms {
                            when "../pir-be/be" {
                            }
                            leaf ms {
                              description
                                "Milli seconds";
                              type empty;
                            }
                          }
                          // conform-action | exceed-action | violate-action
                          uses police-action-grouping;
                        }
                      }
                    }
                  }
                }
                // police rate (control-plane)
                // police rate <units> <pps|bps> [burst <burst-in-x> <packets|bytes>]
                //   [peak-rate <peak-rate-in-xps> <pps|bps>]
                //   [peak-burst <peak-burst-in-x> <packets|bytes>]
                //   [conform-action <action>]
                case police-rate-unit-case {
                  container police-rate-unit {
                    container police {
                      when "../../action-type = 'police'" {
                      }
                      container rate {
                        description
                          "Specify police rate";
                        leaf units {
                          type uint64;
                        }
                        leaf xps {
                          type police-pps-bps-type;
                        }
                        // [burst <burst-in-x> <packets|bytes>]
                        container burst {
                          description
                            "Specify 'burst' parameter";
                          leaf burst-value {
                            type uint32;
                          }
                          leaf burst-type {
                            type police-packets-bytes-type;
                          }
                        }
                        // [peak-rate <peak-rate-in-xps> <pps|bps>]
                        container peak-rate {
                          description
                            "Specify peak rate";
                          leaf peak-rate-value {
                            type uint32 {
                              range "1..512000000";
                            }
                          }
                          leaf xps {
                            type police-pps-bps-type;
                          }
                        }
                        // [peak-burst <peak-burst-in-x> <packets|bytes>]
                        container peak-burst {
                          description
                            "Specify 'peak-burst' parameter for peak-rate";
                          leaf burst-value {
                            type uint32;
                          }
                          leaf burst-type {
                            type police-packets-bytes-type;
                          }
                        }
                        // conform-action | exceed-action | violate-action
                        uses police-action-grouping;
                      }
                    }
                  }
                }
                // police rate percent (control-plane)
                // police rate percent <percentage> [burst <ms> ms]
                //    [peak-rate percent <percentage>] [peak-burst <ms> ms]
                case police-rate-percent-case {
                  container police-rate-percent {
                    container police {
                      when "../../action-type = 'police'" {
                      }
                      container rate {
                        description
                          "Specify police rate";
                        container percent {
                          description
                            "% of interface bandwidth for rate";
                          leaf percentage {
                            type ios-types:percentage;
                          }
                          leaf burst {
                            description
                              "Specify 'burst' parameter";
                            type uint16;
                          }
                          leaf ms {
                            description
                              "Treat 'burst' value in milliseconds";
                            when "../burst";
                            type empty;
                          }
                          container peak-rate {
                            description
                              "Specify peak rate";
                            leaf percent {
                              description
                                "% of interface bandwidth for peak-rate";
                              type ios-types:percentage;
                            }
                          }
                          leaf peak-burst {
                            description
                              "Specify 'peak-burst' parameter for 'peak-rate'";
                            type uint16;
                          }
                          container peak-burst-ms {
                            when "../peak-burst";
                            leaf ms {
                              description
                                "Milli seconds";
                              type empty;
                            }
                          }
                          uses police-action-grouping;
                        }
                      }
                    }
                  }
                }
                // police rate pdp
                // police rate pdp [burst <bytes>]
                //    [peak-rate pdp [peak-burst <bytes>]] ACTIONS
                case police-rate-pdp-case {
                  container police-rate-pdp {
                    container police {
                      when "../../action-type = 'police'" {
                      }
                      container rate {
                        description
                          "Specify police rate";
                        container pdp {
                          description
                            "% of interface bandwidth for rate";
                          leaf burst {
                            description
                              "Conform burst";
                            type police-burst-type;
                          }
                          leaf peak-rate {
                            description
                              "Specify peak rate";
                            type enumeration {
                              enum "pdp";
                            }
                          }
                          leaf peak-burst {
                            description
                              "Specify 'peak-burst' parameter for 'peak-rate'";
                            when "../peak-rate";
                            type police-burst-type;
                          }
                          uses police-action-grouping;
                        }
                      }
                    }
                  }
                }
                // police target-bit-rate  <bits per second>
                case police-target-bitrate-case {
                  container police-target-bitrate {
                    container police {
                      when "../../action-type = 'police'" {
                      }
                      leaf bit-rate {
                        description
                          "Target bit rate (bits per second) (postfix k, m, g optional),decimal point allowed";
                        type uint64 {
                          range "8000..10000000000";
                        }
                      }
                      leaf confirm_burst-byte {
                        description 
                          "Burst Byte";
                        type uint64 {
                          range "100..512000000";
                        }      
                      }
                      leaf excess_burst-byte {
                        description 
                          "Burst Byte";
                        type uint64 {
                          range "100..512000000";
                        }      
                      }
                      leaf conform-action {
                        description
                          "action when rate is less than conform burst";
                        type empty;
                      }
                      leaf transmit {
                        description
                          "transmit packet";
                        type empty;
                      }
                      leaf exceed-action {
                        description
                          "action when rate is within conform and conform + exceed burst";
                        type empty;
                      }
                      leaf drop {
                        description
                          "drop packet";
                        type empty;
                      }
                      leaf set-dscp-transmit {
                        description
                          "set dscp and send it";
                        type empty;
                      }
                      leaf dscp {
                        description
                          "Set packet dscp from dscp";
                        type empty;
                      }
                      leaf table  {
                        description
                          "Specify table-map";
                        type string;
                      }
                      container actions {
                        // policy-map * / class * / police ? / conform-action
                        uses police-conform-action-grouping;
                        // policy-map * / class * / police ? / exceed-action
                        uses police-exceed-action-grouping;
                        // policy-map * / class * / police ? / violate-action
                        uses police-violate-action-grouping;
                      }
                    }
                  }
                }
                // police flow (policy-map)
                // police flow [mask {dest-only | full-flow | src-only}]
                //    <bps> [<burst-normal>] ACTIONS
                case police-flow-case {
                  container police-flow {
                    container police {
                      when "../../action-type = 'police'" {
                      }
                      container flow {
                        description
                          "police each flow";
                        leaf mask {
                          description
                            "flow mask to be used for policing";
                          type enumeration {
                            enum "dest-only";
                            enum "full-flow";
                            enum "src-only";
                          }
                        }
                        leaf bps {
                          type police-bps-type;
                        }
                        leaf burst-normal {
                          type police-burst-type;
                          when "../bps";
                        }
                        uses police-action-grouping;
                      }
                    }
                  }
                }
                // police (Catalyst 4500)
                // police <bps> bps <byte> byte ACTIONS
                case police-catalyst-case {
                  container police-catalyst {
                    container police {
                      when "../../action-type = 'police'" {
                      }
                      leaf bps-value {
                        type string;
                      }
                      leaf bps {
                        type empty;
                      }
                      leaf byte-value {
                        type string;
                      }
                      leaf byte {
                        type empty;
                      }
                      container actions {
                        // policy-map * / class * / police ? / conform-action
                        uses police-conform-action-grouping;
                        // policy-map * / class * / police ? / exceed-action
                        uses police-exceed-action-grouping;
                        // policy-map * / class * / police ? / violate-action
                        uses police-violate-action-grouping;
                      }
                    }
                  }
                }
                // police (Catalyst C3550)
                // police <bps> <burst> exceed-action {drop | policed-dscp-transmit}]
                case police-switch-case {
                  container police-switch {
                    container police {
                      when "../../action-type = 'police'" {
                      }
                      leaf cir {
                        type uint32 {
                          range "8000..1000000000";
                        }
                      }
                      leaf bc {
                        type uint32 {
                          range "8000..2000000";
                        }
                      }
                      leaf exceed-action {
                        description
                          "action when rate is exceeded";
                        type enumeration {
                          enum "drop";
                          enum "policed-dscp-transmit";
                        }
                      }
                    }
                  }
                }
              }
            }
            case priority-case {
              // policy-map * / class * / priority
              container priority {
                when "../action-type = 'priority'";
                leaf level {
                  description
                    "Multi-Level Priority Queue";
                  type uint8 {
                    range "1..2";
                  }
                }
                choice priority-type {
                  leaf kilo-bits {
                    type uint32 {
                      range "8..2000000";
                    }
                  }
                  leaf percent {
                    description
                      "% of total bandwidth";
                    type uint16 {
                      range "1..100";
                    }
                  }
                }
                leaf burst {
                  type uint32 {
                    range "32..64000000";
                  }
                }
              }
            }
            case queue-buffers-case {
              // policy-map * / class * / queue-buffers
              container queue-buffers {
                when "../action-type = 'queue-buffers'";
                leaf ratio {
                  description
                    "Relative buffer size for queue";
                  type uint8 {
                    range "0..100";
                  }
                }
              }
            }
            case queue-limit-case {
              // policy-map * / class * / queue-limit
              container queue-limit {
                when "../action-type = 'queue-limit'";
                leaf queue-limit-value {
                  type uint32 {
                    range "1..8192000";
                  }
                }
                leaf queue-limit-type {
                  type enumeration {
                    enum "bytes";
                    enum "ms";
                    enum "packets";
                    enum "us";
                  }
                }
              }
              container queue-limit-dscp {
                when "../action-type = 'queue-limit'";
                list dscp {
                  description
                    "parameters for each dscp value";
                  key dscp-val;
                  leaf dscp-val {
                    type ios-types:dscp-type;
                  }
                  leaf values {
                    description
                      "dscp values";
                    type empty;
                  }
                  leaf dscp-val1 {
                    type ios-types:dscp-type;
                  }
                  leaf percent {
                    description
                      "% of threshold";
                    type uint8 {
                      range "0..100";
                    }
                  }
                }
              }
            }
            case random-detect {
              // policy-map * / class * / random-detect
              container random-detect {
                when "../action-type = 'random-detect'";
                container aggregate {
                  description
                    "aggregate subclasses";
                  presence "true";
                  leaf minimum-thresh {
                    description
                      "minimum threshold for red aggregate";
                    type uint32 {
                      range "0..1000000";
                    }
                  }
                  leaf maximum-thresh {
                    description
                      "maximum threshold for red aggregate";
                    type uint32 {
                      range "0..1000000";
                    }
                  }
                  leaf mark-probability {
                    description
                      "mark-probability for red aggregate";
                    type empty;
                  }
                  leaf denominator {
                    type uint32 {
                      range "0..65535";
                    }
                  }
                }
                leaf cos-based {
                  description
                    "Enable cos-class-based WRED as drop policy, supported on ASR9xx platform only";
                  type empty;
                }
                container cos {
                  description
                    "parameters for each cos value, supported on ASR9xx platform only";
                  leaf cos-val {
                    type uint16 {
                      range "0..7";
                    }
                  }
                  uses random-detect-grouping;
                }
                leaf discard-class-based {
                  description
                    "Enable discard-class-based WRED as drop policy";
                  type empty;
                }
                container discard-class {
                  description
                    "parameters for each discard-class value";
                  leaf dclass {
                    type uint16 {
                      range "0..7";
                    }
                  }
                  uses random-detect-grouping;
                }
                leaf dscp-based {
                  description
                    "Enable dscp-based WRED as drop policy";
                  type empty;
                }
                list dscp {
                  description
                    "parameters for each dscp value";
                  key "dscp-val";
                  leaf dscp-val {
                    type ios-types:dscp-type;
                  }
                  uses random-detect-grouping;
                }
                leaf ecn {
                  description
                    "explicit congestion notification";
                  type empty;
                }
                leaf exponential-weighting-constant {
                  description
                    "weight for mean queue depth calculation";
                  type uint16 {
                    range "1..16";
                  }
                }
                // Note: "random-detect precedence-based" in show running is "random-detect".
                // Full sync on "random-detect precedence-based".
                // Caveat: "no random-detect precedence-based" cannot be supported".
                leaf precedence-based {
                  description
                    "Enable precedence-based WRED as drop policy";
                  type empty;
                }
                container precedence {
                  description
                    "parameters for each precedence value";
                  leaf prec {
                    type precedence-type2;
                  }
                  uses random-detect-grouping;
                }
              }
            }
            case service-policy-case {
              // policy-map * / class * / service-policy
              leaf service-policy {
                type string;
              }
            }
            case set-case {
              // policy-map * / class * / set
              container set {
                when "../action-type = 'set'";
                // policy-map * / class * / set atm-clp
                leaf atm-clp {
                  description
                    "Set ATM CLP bit to 1";
                  type empty;
                }
                // policy-map * / class * / set cos
                container cos {
                  description
                    "Set IEEE 802.1Q/ISL class of service/user priority";
                  choice cos-type {
                    case a {
                      leaf val {
                        type uint16 {
                          range "0..7";
                        }
                      }
                    }
                    case b {
                      leaf pack {
                        type enumeration {
                          enum "dscp" {
                          }
                          enum "precedence" {
                          }
                          enum "cos";
                          enum "qos-group";
                          enum "wlan";
                        }
                      }
                      leaf user-priority {
                        description
                          "Set value from WLAN user-priority";
                        when "../pack = 'wlan'";
                        type empty;
                      }
                      leaf table {
                        description
                          "Set codepoint value based on tablemap.";
                        type string;
                      }
                    }
                  }
                }
                // policy-map * / class * / set discard-class
                leaf discard-class {
                  description
                    "Discard behavior identifier";
                  type uint16 {
                    range "0..7";
                  }
                }
                // policy-map * / class * / set dscp
                container dscp {
                  description
                    "Set DSCP in IP(v4) and IPv6 packets";
                  container dscp {
                    description
                      "Set packet dscp from dscp";
                    presence true;
                    leaf table {
                      description
                        "Set packet dscp from dscp based on table map.";
                      type string;
                    }
                  }
                  leaf tunnel {
                    description
                      "set tunnel packet dscp";
                    type empty;
                  }
                  leaf dscp-val {
                    type ios-types:dscp-type;
                  }
                }
                // policy-map * / class * / set fr-de
                leaf fr-de {
                  description
                    "Set FR DE bit to 1";
                  type empty;
                }
                // policy-map * / class * / set ip
                container ip {
                  description
                    "Set IP specific values";
                  choice ip-choice {
                    container dscp {
                      description
                        "Set IP DSCP (DiffServ CodePointint)";
                      leaf tunnel {
                        description
                          "set tunnel packet dscp";
                        type empty;
                      }
                      leaf dscp-val {
                        type ios-types:dscp-type;
                      }
                    }
                    container precedence {
                      description
                        "Set IP precedence";
                      presence "Set IP precedence";
                      leaf precedence-val {
                        type ios-types:precedence-type;
                      }
                    }
                  }
                }
                // policy-map * / class * / set mpls
                container mpls {
                  description
                    "Set MPLS specific values";
                  container experimental {
                    description
                      "Set Experimental value";
                    container imposition {
                      description
                        "Set Experimental value at tag imposition";
                      leaf exp-value {
                        type uint8 {
                          range "0..7";
                        }
                      }
                      // dscp
                      // precedence
                    }
                    container topmost {
                      description
                        "Set Experimental value  on topmost label";
                      leaf exp-value {
                        type uint8 {
                          range "0..7";
                        }
                      }
                    }
                  }
                }
                // policy-map * / class * / set qos-group
                container qos-group {
                  description
                    "Set QoS Group";
                  leaf qos-group-value {
                    type uint8 {
                      range "0..99";
                    }
                  }
                  // dscp
                  // mpls
                  // precedence
                }
              }
            }
            case shape-case {
              // policy-map * / class * / shape
              container shape {
                when "../action-type = 'shape'";
                // policy-map * / class * / shape adaptive
                leaf adaptive {
                  description
                    "Enable Traffic Shaping adaptation to BECN";
                  type uint32 {
                    range "8000..154400000";
                  }
                }
                // policy-map * / class * / shape average
                container average {
                  description
                    "configure token bucket: CIR (bps) [Bc (bits) [Be (bits)]], send out Bc only per interval";
                  choice average-choice {
                    case a {
                      leaf bit-rate {
                        type uint64;
                        //range "8000..154400000";
                      }
                      leaf bits-per-interval-sustained {
                        type uint32 {
                          range "256..154400000";
                        }
                      }
                      leaf bits-per-interval-excess {
                        when "../bits-per-interval-sustained";
                        type uint32 {
                          range "0..154400000";
                        }
                      }
                      container account {
                        description 
                          "Overhead Accounting";
                        leaf user-defined {
                          description 
                            "Offset Size";
                          type int32 {
                            range "-1000000..1000000";
                          }
                        }
                      }
                    }
                    case b {
                      leaf percent {
                        description
                          "% of interface bandwidth for Committed information rate";
                        type ios-types:percentage;
                      }
                      leaf burst-size-sustained {
                        type uint16 {
                          range "10..2000";
                        }
                      }
                      leaf ms {
                        description
                          "milliseconds";
                        type empty;
                      }
                      container bse {
                        leaf burst-size-excess {
                          type uint16 {
                            range "10..2000";
                          }
                        }
                        leaf ms {
                          description
                            "milliseconds";
                          type empty;
                        }
                      }
                    }
                  }
                }
                // policy-map * / class * / shape fecn-adapt
                leaf fecn-adapt {
                  description
                    "Enable Traffic Shaping reflection of FECN as BECN";
                  type empty;
                }
                // policy-map * / class * / shape fr-voice-adapt
                container fr-voice-adapt {
                  description
                    "Enable rate adjustment depending on voice presence";
                  presence "Enable rate adjustment depending on voice presence";
                  leaf deactivation {
                    type uint16 {
                      range "1..10000";
                    }
                  }
                }
                // policy-map * / class * / shape max-buffers
                leaf max-buffers {
                  description
                    "Set Maximum Buffer Limit";
                  type uint16 {
                    range "1..4096";
                  }
                }
              }
            }
            case trust-case {
              // policy-map * / class * / trust
              leaf trust {
                when "../action-type = 'trust'";
                type enumeration {
                  enum "cos";
                  enum "dscp";
                  enum "ip-precedence";
                }
              }
            }
          }
        }
      }
      // policy-map * / description
      leaf description {
        description
          "Policy-Map description";
        type string {
          length "1..200";
        }
      }
      // policy-map * /sequence-interval
      leaf sequence-interval {
        description
          "Enable sequence number capability";
        when "../type = 'appnav'";
        type uint16;
      }
    }
  }

  grouping class-map-match-result-type-grouping {
    leaf aaa-timeout {
      description
        "aaa timeout type";
      type empty;
    }
    leaf agent-not-found {
      description
      "agent not found type";
      type empty;
    }
    leaf authoritative {
      description
      "failure type";
      type empty;
    }
    leaf method-timeout {
      description
      "method_timeout type";
      type empty;
    }
    leaf none {
      description
      "no type";
      type empty;
    }
    leaf success {
      description
      "success type";
      type empty;
    }
  }

  grouping class-map-control-filter-grouping {
    list activated-service-template {
      description
        "match name of service template activated on session";
      key "service-name";
      leaf service-name {
        description "Enter service name";
        type string;
      }
    }
    container authorization-status {
      description
        "match the authorization status of the session";
      leaf authorized {
        description
          "authorized";
        type empty;
      }
      leaf unauthorized {
        description
          "unauthorized";
        type empty;
      }
    }
    container authorizing-method-priority {
      description
        "match the priority against the authorizing method's priority";
      leaf eq {
        description
          "equal to";
        type uint8 {
          range 1..254;
        }
      }
      leaf gt {
        description
          "greater than";
        type uint8 {
          range 1..254;
        }
      }
      leaf lt {
        description
          "less than";
        type uint8 {
          range 1..254;
        }
      }
    }
    container method {
      description "match the type of authentication method from an event";
      leaf dot1x {
          description
            "dot1x";
          type empty;
      }
      leaf mab {
          description
            "mab";
          type empty;
      }
      leaf webauth {
          description
            "webauth";
          type empty;
      }
    }
    container result-type {
      description
        "match the result type, optionally for a specific method";
      container method {
        description
          "match the result of a particular method";
        container dot1x {
          description
            "dot1x result";
          uses class-map-match-result-type-grouping;
        }
        container mab {
          description
            "mab result";
          uses class-map-match-result-type-grouping;
        }
        container webauth {
          description
            "webauth result";
          uses class-map-match-result-type-grouping;
        }
      }
      uses class-map-match-result-type-grouping;
    }
  }

  grouping class-map-match-grouping {
    // class-map * / match current-method-priority
    container current-method-priority {
      description
        "match the priority against the current method's priority";
      leaf eq {
        description
          "equal to";
        type uint8 {
          range "1..254";
        }
      }
      leaf gt {
        description
          "greater than";
        type uint8 {
          range "1..254";
        }
      }
      leaf lt {
        description
          "less than";
        type uint8 {
          range "1..254";
        }
      }
    }
    // class-map * / match application
    container application {
      description
        "Application to match";
      container application-group {
        description
          "Application Group to match";
        leaf telepresence-group {
          description
            "Telepresence Group";
          type empty;
        }
        leaf vmware-group {
          description
            "VMWARE Group";
          type empty;
        }
        leaf webex-group {
          description
            "WebEx Group";
          type empty;
        }
      }
      container attribute {
        description
          "Application attribute to match";
        leaf media-type {
          description
            "Media type attribute to match";
          type enumeration {
            enum "audio";
            enum "audio-video";
            enum "control";
            enum "data";
            enum "video";
          }
        }
      }
    }
    // class-map * / match access-group
    container access-group {
      description
        "Access group";
      leaf index {
        type uint32 {
          range "1..2699";
        }
      }
      leaf-list name {
        description
          "Named Access List";
        type string;
      }
    }
    // class-map * / match any
    leaf any {
      description
        "Any packets";
      type empty;
    }
    // class-map * / match class-map
    leaf-list class-map {
      description
        "Class map";
      type string;
//      type leafref {
//        path "/ios:native/class-map/name";
//      }
    }
    // class-map * / match cos
    leaf-list cos {
      description
        "IEEE 802.1Q/ISL class of service/user priority values";
      type uint8 {
        range "0..7";
      }
    }
    // class-map * / match destination-address
    container destination-address {
      description
        "Destination address";
      leaf-list mac {
        description
          "MAC address";
        type yang:mac-address;
      }
    }
    // class-map * / discard-class
    leaf-list discard-class {
      description
        "Discard behavior identifier";
      type uint8 {
        range "0..7";
      }
    }
    // class-map * / dscp
    leaf-list dscp {
      description
        "Match DSCP in IP(v4) and IPv6 packets";
      type ios-types:dscp-type;
    }
    // class-map * / fr-de
    leaf fr-de {
      description
        "Match on Frame-relay DE bit";
      type empty;
    }
    // class-map * / fr-dlci
    leaf-list fr-dlci {
      description
        "Match on fr-dlci";
      type uint16 {
        range "16..1007";
      }
    }
    // class-map * / group-object
    container group-object {
      description
        "Match object-group";
      container security {
        description
          "Match object-group security";
        leaf-list source {
          description
            "Match source object-group security";
          type string;
        }
        leaf-list destination {
          description
            "Match destination object-group security";
          type string;
        }
      }
    }
    // class-map * / input-interface
    leaf-list input-interface {
      description
        "Select an input interface to match";
      type string;
    }
    // class-map * / ip
    container ip {
      description
        "IP specific values";
      leaf-list dscp {
        description
          "Match IP DSCP (DiffServ CodePoints)";
        type ios-types:dscp-type;
      }
      // class-map * / ip precedence
      leaf-list precedence {
        description
          "Match IP precedence";
        type ios-types:precedence-type;
      }
      // class-map * / ip rtp
      list rtp {
        description
          "Match RTP port nos";
        key "port1 port2";
        leaf port1 {
          type uint16 {
            range "2000..65535";
          }
        }
        leaf port2 {
          type uint16 {
            range "0..16383";
          }
        }
      }
    }
    // class-map * / non-client-nrt
    leaf non-client-nrt {
      type empty;
    }
    // class-map * / mpls
    container mpls {
      description
        "Multi Protocol Label Switching specific values";
      container experimental {
        description
          "Match MPLS experimental";
        leaf-list topmost {
          description
            "Match MPLS experimental value on topmost label";
          type uint8 {
            range "0..7";
          }
        }
      }
    }
    // class-map * / packet
    container packet {
      description
        "Layer 3 Packet length";
      container length {
        description
          "Layer 3 Packet length";
        leaf max {
          description
            "Maximum length of packet";
          type uint16 {
            range "1..2000";
          }
        }
        leaf min {
          description
            "Minimum length of packet";
          type uint16 {
            range "1..2000";
          }
        }
      }
    }
    // class-map * / precedence
    leaf-list precedence {
      description
        "Match Precedence in IP(v4) and IPv6 packets";
      type ios-types:precedence-type;
    }
    // class-map * / protocol
    container protocol {
      description
        "Protocol";
      list protocols-list {
        key "protocols";
        leaf protocols {
          type string;
        }
      }
      container attribute {
        description  "Attribute based protocol match";
        list application-group {
          description "Application-group attribute";
          key "name";
          leaf name {
            type string;
          }
        }
        list application-set {
          description "Application-set attribute";
          key "name";
          leaf name {
            type string;
          }
        }
        list business-relevance {
          description "Application business-relevance";
          key "name";
          leaf name {
            type string;
          }
        }
        list category {
          description "Category attribute";
          key "name";
          leaf name { 
            type string;
          }
        }
        list encrypted {
          description "Encrypted applications";
          key "name";
          leaf name {
            type string;
          }
        }
        list sub-category {
          description "Sub-category attribute";
          key "name";
          leaf name {
            type string;
          }
        }
        list traffic-class {
          description "SRND class";
          key "name";
          leaf name {
            type string;
          }
        }
        list tunnel {
          description "Tunnelled applications";
          key "name";
          leaf name {
            type string;
          }
        } 
      }
    }
    // class-map * / qos-group
    leaf-list qos-group {
      description
        "Qos-group";
      type uint16 {
        range "0..99";
      }
    }
    // class-map * / match security-group
    container security-group {
      description
        "Security group";
      container destination {
        description
          "Destination security group";
        leaf tag {
          description
            "Security group tag";
          type uint16;
        }
      }
      container source {
        description
          "Source security group";
        leaf tag {
          description
            "Security group tag";
          type uint16;
        }
      }
    }
    // class-map * / service
    list service {
      description
        "Service Instance to match";
      key efp;
      leaf efp {
        type uint16 {
          range "1..4000";
        }
      }
      leaf instance {
        description
          "Service Instance to match";
        type empty;
      }
      leaf ethernet {
        description
          "Service Instance to match";
        type empty;
      }
    }
    // class-map * / source-address
    container source-address {
      description
        "Source address";
      leaf-list mac {
        description
          "MAC address";
        type yang:mac-address;
      }
    }
    // class-map * / match vlan
    container vlan {
      description
        "VLANs to match";
      leaf-list inner {
        description
          "Inner tag to match";
        type union {
          type uint16 {
            range "1..4094";
          }  
          type string;
        }
      }
      leaf-list value {
        type union {
          type uint16 {
            range "1..4094";
          }   
          type string;
        }   
      }
    }
  }//class-map-match-grouping

  grouping class-map-appnav-match-grouping { //4716
    leaf peer {
      description
        "APPNAV Peer Filter";
      when "../../type = 'appnav'";
      type string;
    }
  }

  grouping class-map-appnav-not-match-grouping { //4725
    leaf peer {
      description
        "APPNAV Peer Filter";
      when "../../../type = 'appnav'";
      type string;
    }
  }

  grouping config-class-map-grouping {
    list class-map {
      description
        "configure qos class map";
      key "name";
      leaf name {
        type string;
      }
      // class-map * type inspect
      leaf type {
        description
          "type of the class-map";
        type enumeration {
          enum "access-control";
          enum "appnav";
          enum "control";
          enum "inspect";
          enum "multicast-flows";
          enum "stack";
          enum "traffic";
        }
      }
      leaf subscriber {
        type empty;
      }
      // class-map * <protocol>
      leaf protocol {
        when "../type = 'inspect'";
        type enumeration {
          enum "aol";
          enum "edonkey";
          enum "fasttrack";
          enum "gnutella";
          enum "http";
          enum "imap";
          enum "kazaa2";
          enum "msnmsgr";
          enum "pop3";
          enum "smtp";
          enum "sunrpc";
          enum "ymsgr";
        }
      }
      // class-map * <match-any|match-all>
      leaf prematch {
        type enumeration {
          enum "match-all";
          enum "match-any";
          enum "match-none";
        }
        mandatory true;
      }
      // class-map * / description
      leaf description {
        description
          "Class-Map description";
        type string;
      }
      // class-map * / match
      container match {
        description
          "classification criteria";
        uses class-map-match-grouping;
        uses class-map-appnav-match-grouping;
        uses class-map-control-filter-grouping;
        container not {
          description
            "Negate this match result";
          uses class-map-match-grouping;
          uses class-map-appnav-not-match-grouping;
        }
      }
      container no-match {
        description "no-match filter";
        uses class-map-control-filter-grouping;
      }
    }
  }

  grouping config-parameter-map-grouping {
    container opendns {
      when "/ios:native/ios:parameter-map/ios:type = 'opendns'";
      list local-domain {
        description
          "Local domain processing";
        key regexp;
        leaf regexp {
          type string;
        }
      }
    }
    container regex {
      when "/ios:native/ios:parameter-map/ios:type = 'regex'";
      list pattern {
        description
          "Configure pattern to match";
        key regexp;
        leaf regexp {
          type string;
        }
      }
    }
    container virtual-ip {
      description
        "Virtual Ip Address";
      container ipv4 {
        description
          "Ipv4 Address";
        leaf address {
          description "Recovery IP address";
          type inet:ipv4-address;
        }
        leaf virtual-host {
          description
            "WEBAUTH Timeout in Seconds";
          type string;
        }
      }
      container ipv6 {
        description
          "Ipv6 Address";
        leaf address {
          description "Recovery IP address";
          type inet:ipv6-address;
        }
        leaf virtual-host {
          description
            "WEBAUTH Timeout in Seconds";
          type string;
        }
      }
    }
    leaf intercept-https-enable {
      description
        "Enable intercept of https traffic";
      type empty;
    }
    leaf captive-bypass-portal {
      description
        "Turn on captive bypass";
      type empty;
    }
    leaf success-window-disable {
      description
        "Disable Success Window";
      type empty;
    }
    leaf max-http-conns {
      description
        "Webauth max HTTP connections per client";
      type uint8 {
        range "1..200";
      }
    }
    container consent {
      description
        "consent parameters";
      leaf email {
        description
          "Turn-on Consent with Email";
        type empty;
      }
    }
    container custom-page {
      description
        "Sleep timeout in Minute";
      container login {
        description
          "Sleep timeout in Minute";
        leaf device {
          type string;
        }
        container expired {
          description
            "Sleep timeout in Minute";
          leaf device {
            type string;
          }
        }
      }
      container failure {
        description
          "Sleep timeout in Minute";
        leaf device {
          type string;
        }
      }
      container success {
        description
          "Sleep timeout in Minute";
        leaf device {
          type string;
        }
      }
    }
    container login-auth-bypass {
      description
        "Sleep timeout in Minute";
      container ip-access-list {
        description
          "vrf binding with parameter map";
        leaf name {
          type string;
        }
        leaf domain-name-list {
          description
            "vrf binding with parameter map";
          type string;
        }
      }
    }
    container redirect {
      description
        "enable sleeping client for webauth";
      container append {
        description
          "Sleep timeout in Minute";
        container ap-mac {
          description
            "Sleep timeout in Minute";
          leaf tag {
            type string;
          }
        }
        container client-mac {
          description
            "Sleep timeout in Minute";
          leaf tag {
            type string;
          }
        }
        container wlan-ssid {
          description
            "Sleep timeout in Minute";
          leaf tag {
            type string;
          }
        }
      }
      container portal {
        description
          "Sleep timeout in Minute";
        leaf ipv4 {
          type inet:ipv4-address;
        }
        leaf ipv6 {
          type inet:ipv6-address;
        }
      }
      leaf for-login {
        type string;
      }
      leaf on-failure {
        type string;
      }
      leaf on-success {
        type string;
      }
    }
    container sleeping-client {
      description
        "enable sleeping client for webauth";
      leaf timeout {
        description
          "Sleep timeout in Minute";
        type uint32 {
          range "60..3932100";
        }
      }
    }
    container timeout {
      description
        "timeout for the webauth session";
      when "/ios:native/ios:parameter-map/ios:type = 'webauth'";
      container init-state {
        description
          "init-state timeout";
        presence true;
        leaf sec {
          description
            "WEBAUTH Timeout in Seconds";
          type uint32 {
            range "60..3932100";
          }
        }
      }
      container fin-wait {
        description
          "fin-wait timeout";
        leaf msec {
          description
            "WEBAUTH Timeout in milliseconds";
          type uint32 {
            range "1..2147483647";
          }
        }
      }
    }
    container watch-list {
      description
        "Watch List of webauth clients";
      when "/ios:native/ios:parameter-map/ios:type = 'webauth'";
      leaf enabled {
        description
          "Enable Watchlist";
        type empty;
      }
      leaf dynamic-expiry-timeout {
        description
          "dynamic_expiry_timeout";
        type uint32 {
          range "0..2147483";
        }
      }
      container add-item {
        description
          "Add item to Watch-list";
        leaf ipv4 {
          description
            "IPv4 Watch List Entry";
          type inet:ipv4-address;
        }
        leaf ipv6 {
          description
            "IPv6 Watch List Entry";
          type inet:ipv6-address;
        }
      }
    }
    container aggressive-aging {
      description
        "Aggressive Aging parameters";
      when "/ios:native/ios:parameter-map/ios:type = 'inspect-global'";
      container high {
        description
          "Specify the high watermark for aggressive-aging";
        choice absolute-percent {
          case absolute-case {
            container absolute {
              leaf value {
                type uint64 {
                  range "1..4294967295";
                }
              }
              leaf low {
                description
                  "Specify the low watermark for aggressive-aging";
                type uint64 {
                  range "1..4294967295";
                }
              }
            }
          }
          case percent-case {
            container percent {
              description
                "high watermark in percentage of max-incomplete value";
              leaf value {
                type uint8 {
                  range "1..100";
                }
              }
              leaf low_percent {
                description
                  "Specify the low watermark for aggressive-aging in percents";
                type uint8 {
                  range "1..100";
                }
              }
            }
          }
        }
      }
    }
    leaf alert {
      description
        "Turn on/off alert";
      type enumeration {
        enum "off";
        enum "on";
      }
    }
    leaf application-inspect {
      description
        "Turn on application inspection";
      type enumeration {
        enum "all";
        enum "dns";
        enum "exec";
        enum "ftp";
        enum "gtp";
        enum "h323";
        enum "http";
        enum "imap";
        enum "login";
        enum "msrpc";
        enum "netbios";
        enum "pop3";
        enum "rtsp";
        enum "shell";
        enum "sip";
        enum "skinny";
        enum "smtp";
        enum "sunrpc";
        enum "tftp";
      }
    }
    leaf audit-trail {
      description
        "Turn on/off audit trail";
      when "/ios:native/ios:parameter-map/ios:type = 'inspect'";
      type enumeration {
        enum "off";
        enum "on";
      }
    }
    leaf dns-timeout {
      description
        "Specify timeout for DNS";
      when "/ios:native/ios:parameter-map/ios:type = 'inspect'";
      type uint32 {
        range "1..2147483";
      }
    }
    container global {
      description
        "cws_tunnel global parameter-map";
      leaf fail-open {
        description
          "Allow traffic to go in clear if CWS Towers are unreachable";
        when "/ios:native/ios:parameter-map/ios:type = 'cws-tunnel'";
        type empty;
      }
      container license {
        description
          "License Key";
        when "/ios:native/ios:parameter-map/ios:type = 'cws-tunnel'";
        container Unencypted {
          description
            "Unencrypted License";
          leaf Hex-string {
            description
              "32 char non encrypted hex key";
            type string;
          }
        }
        container Encrypted {
          description
            "Encrypted License";
          leaf Hex-string {
            description
              "66 char encrypted hex key";
            type string;
          }
        }
      }
      leaf logging {
        description
          "CWS syslogs";
        type empty;
      }
      container primary {
        description
          "Primary tower";
        when "/ios:native/ios:parameter-map/ios:type = 'cws-tunnel'";
        presence true;
        container tower {
          description
            "Tower configuration for CWS";
          leaf ipv4 {
            description
              "IPv4 address of the tower";
            type inet:ipv4-address;
          }
          leaf name {
            description
              "Fully Qualified Domain Name of tower";
            type string;
          }
        }
      }
      leaf redirect-list {
        description
          "Set access-list for reverse route from CWS Tower
          Standard IP access-list number <1-199>
          Standard IP access-list number (expanded range) <1300-2699>";
        when "/ios:native/ios:parameter-map/ios:type = 'cws-tunnel'";
        type union {
          type uint16 {
            range "1..199";
          }
          type uint16 {
            range "1300..2699";
          }
        }
      }
      container secondary {
        description
          "Secondary tower";
        when "/ios:native/ios:parameter-map/ios:type = 'cws-tunnel'";
        presence true;
        container tower {
          description
            "Tower configuration for CWS";
          leaf ipv4 {
            description
              "IPv4 address of the tower";
            type inet:ipv4-address;
          }
          leaf name {
            description
              "Fully Qualified Domain Name of tower";
            type string;
          }
        }
      }
      container whitelist {
        description
          "Disable redirection to CWS
           Access list (standard) <1-199>
           Access list (extended) <1300-2699>
           Access list name";
        presence true;
        container acl {
          description
            "Access list";
          leaf acl-number {
            type union {
              type uint16 {
                range "1..199";
              }
              type uint16 {
                range "1300..2699";
              }
            }
          }
          leaf name {
            description
              "Access list name";
            type string;
          }
        }
        container domain-name {
          description
            "Domain name based Whitelist";
          leaf regex {
            description
              "Domain name regex parameter map";
            type string;
          }
        }
        container download {
          description
            "whitelist download command";
          presence true;
          leaf interval {
            description
              "Download interval in minutes";
            type uint16 {
              range "5..10080";
            }
          }
        }
      }
    }
    container icmp {
      description
        "Config timeout values for icmp";
      when "/ios:native/ios:parameter-map/ios:type = 'inspect'";
      leaf idle-time {
        description
          "Specify timeout for icmp";
        type uint32 {
          range "1..2147483";
        }
      }
    }
    container lisp {
      description
        "Turn on LISP options";
      leaf inner-packet-inspection {
        description
          "inner-packet-inspection";
        type empty;
      }
    }
    container log {
      description
        "Configure inspect logging parameters";
      leaf dropped-packets {
        description
          "Log dropped packets";
        type empty;
      }
      container flow-export {
        description
          "Configure inspect external logging parameters";
        container template {
          description
            "Configure record template parameters";
          leaf timeout-rate {
            description
              "Rate to resend the template in seconds";
            type uint32 {
              range "0..65535";
            }
          }
        }
        container v9 {
          description
            "Netflow version 9";
          container udp {
            description
              "Use UDP to export records";
            container destination {
              description
                "Specify the flow-export destination";
              leaf dst-ip {
                type inet:ipv4-address;
              }
              leaf dst-port {
                type uint16;
              }
            }
          }
        }
      }
    }
    leaf max-destination {
      description
        "config maximum destination";
      when "/ios:native/ios:parameter-map/ios:type = 'inspect-zone'";
      type uint32 {
        range "1..4294967295";
      }
    }
    container max-incomplete {
      description
        "Specify maximum number of incomplete connections before clamping";
      leaf high {
        description
          "Specify high-watermark for clamping";
        type uint32 {
          range "1..2147483647";
        }
      }
      leaf low {
        description
          "Specify low-watermark for clamping";
        type uint32 {
          range "1..2147483647";
        }
      }
    }
    container one-minute {
      description
        "Specify one-minute-sample watermarks for clamping";
      when "/ios:native/ios:parameter-map/ios:type = 'inspect'";
      leaf high {
        description
          "Specify high-watermark for clamping";
        type uint32 {
          range "1..2147483647";
        }
      }
      leaf low {
        description
          "Specify low-watermark for clamping";
        type uint32 {
          range "1..2147483647";
        }
      }
    }
    container sessions {
      description
        "Maximum number of inspect sessions";
      when "/ios:native/ios:parameter-map/ios:type = 'inspect'";
      leaf maximum {
        description
          "Maximum sessions";
        type uint32 {
          range "1..2147483647";
        }
      }
      container queue {
        description
          "queue";
        leaf max-threshold {
          type uint16 {
            range "0..65535";
          }
        }
        leaf min-threshold {
          type uint16 {
            range "0..65535";
          }
        }
      }
    }

    choice tcp-ins {
      container tcp-inspect {
        when "/ios:native/ios:parameter-map/ios:type = 'inspect'";
        container tcp {
          description
          "Config timeout values for tcp connections";
          when "/ios:native/ios:parameter-map/ios:type = 'inspect'";
          leaf finwait-time {
            description
            "Specify timeout for TCP connections after a FIN";
            type uint32 {
              range "1..2147483";
            }
          }
          leaf idle-time {
            description
              "Specify idle timeout for tcp connections";
            type uint32 {
              range "1..2147483";
            }
          }
          container max-incomplete {
            description
              "Specify max half-open connection per host";
            leaf host {
              description
                "Specify max half-open connection per host";
              type uint32 {
                range "1..4294967295";
              }
            }
          }
          leaf synwait-time {
            description
              "Specify timeout for TCP connections after a SYN and no";
            type uint32 {
              range "1..2147483";
            }
          }
        }
      }
      container tcp-inspect-zone {
        when "/ios:native/ios:parameter-map/ios:type = 'inspect-zone'";
        container tcp {
          description
            "Configure tcp syn-flood per-destination rate";
          container syn-flood {
            description
              "maximum syn packet";
            container rate {
              description
                "maximum syn packet rate";
              leaf per-destination {
                description
                  "per destination
                   maximum rate of TCP SYN packets";
                type uint32 {
                  range "1..1000000000";
                }
              }
            }
          }
        }
      }
    }

    container threat-detection {
      description
        "Configure Threat Detection";
      when "/ios:native/ios:parameter-map/ios:type = 'inspect-zone'";
      leaf basic-threat {
        description
          "Enable Threat Detection";
        type empty;
      }
      container rate {
        description
          "Configure Threat Detection rate";
        container fw-drop {
          description
            "Configure Threat Detection rate for firewall drop events";
          leaf average-time-frame {
            description
              "Configure Threat Detection average time frame";
            type uint32 {
              range "600..3600";
            }
          }
          leaf average-threshold {
            description
              "Configure Threat Detection average threshold";
            type uint64 {
              range "1..4294967295";
            }
          }
          leaf burst-threshold {
            description
              " Configure Threat Detection burst threshold";
            type uint64 {
              range "1..1000000000";
            }
          }
        }
        container inspect-drop {
          description
            "Configure Threat Detection rate for firewall inspection based drop events";
          leaf average-time-frame {
            description
              "Configure Threat Detection average time frame";
            type uint32 {
              range "600..3600";
            }
          }
          leaf average-threshold {
            description
              "Configure Threat Detection average threshold";
            type uint64 {
              range "1..4294967295";
            }
          }
          leaf burst-threshold {
            description
              " Configure Threat Detection burst threshold";
            type uint64 {
              range "1..1000000000";
            }
          }
        }
        container syn-attack {
          description
            "Configure Threat Detection rate for syn attack events";
          leaf average-time-frame {
            description
              "Configure Threat Detection average time frame";
            type uint32 {
              range "600..3600";
            }
          }
          leaf average-threshold {
            description
              "Configure Threat Detection average threshold";
            type uint64 {
              range "1..4294967295";
            }
          }
          leaf burst-threshold {
            description
              " Configure Threat Detection burst threshold";
            type uint64 {
              range "1..1000000000";
            }
          }
        }
      }
    }
    container udp {
      description
        "Config timeout values for udp flows";
      when "/ios:native/ios:parameter-map/ios:type = 'inspect'";
      leaf idle-time {
        description
          "Specify idle timeout for udp";
        type uint32 {
          range "1..2147483";
        }
      }
    }
    container vrf {
      description
        "vrf binding with parameter map";
      leaf name {
        type string;
      }
      leaf inspect {
        description
          "vrf binding with parameter map";
        type string;
      }
    }
    leaf zone-mismatch {
      description
        "Config zone-mismatch option";
      type enumeration {
        enum "drop";
      }
    }
  }

  grouping config-service-policy-direction-grouping {
    leaf input {
      description
        "Assign policy-map to the input of an interface";
      type string;
    }
    leaf output {
      description
        "Assign policy-map to the output of an interface";
      type string;
    }
  }

  grouping config-service-policy-grouping {
    container service-policy {
      uses config-service-policy-direction-grouping;
    }
  }

  grouping config-interface-service-policy-grouping {
    container service-policy {
      description
        "Configure QoS Service Policy";
      leaf history {
        description
          "Keep history of QoS metrics";
        type empty;
      }
      uses config-service-policy-direction-grouping;
      container type {
        description
          "Configure CPL Service Policy";
        container control {
          leaf subscriber {
            type string;
          }
        }
        container performance-monitor {
          description
            "Configure media monitor service-policy type";
          leaf direction {
            type enumeration {
              enum "input";
              enum "output";
            }
          }
          leaf name {
            type string;
          }
        }
        // interface * / service-policy type * / service-chain
        container service-chain {
          description
            "Configure Service-chain Service Policy";
           container input {
               description "Assign policy-map to the input of an interface";
               leaf name {
                  type string;
               }
            }
           container output {
               description "Assign policy-map to the output of an interface";
               leaf name {
                  type string;
               }
           }
        }
      }
    }

  }

  /////////////////////////////////////////////////////////
  // native / policy
  /////////////////////////////////////////////////////////
  augment "/ios:native/ios:policy" {
    uses config-class-map-grouping;
    uses config-policy-map-grouping;
  }

  /////////////////////////////////////////////////////////
  // native / parameter-map
  /////////////////////////////////////////////////////////
  augment "/ios:native/ios:parameter-map" {
    uses config-parameter-map-grouping {
      if-feature ios-features:parameter-map;
    }
  }

  /////////////////////////////////////////////////////////
  // native / control-plane
  /////////////////////////////////////////////////////////
  augment "/ios:native/ios:control-plane" {
    uses config-service-policy-grouping;
  }

  /////////////////////////////////////////////////////////
  // native / interface * / service-policy
  /////////////////////////////////////////////////////////
  augment "/ios:native/ios:interface/ios:FastEthernet" {
    uses config-interface-service-policy-grouping;
  }

  augment "/ios:native/ios:interface/ios:GigabitEthernet" {
    uses config-interface-service-policy-grouping;
  }

  augment "/ios:native/ios:interface/ios:TenGigabitEthernet" {
    uses config-interface-service-policy-grouping;
  }

  augment "/ios:native/ios:interface/ios:FiveGigabitEthernet" {
    uses config-interface-service-policy-grouping;
  }

  augment "/ios:native/ios:interface/ios:TwentyFiveGigE" {
    uses config-interface-service-policy-grouping;
  }

  augment "/ios:native/ios:interface/ios:FortyGigabitEthernet" {
    uses config-interface-service-policy-grouping;
  }

  augment "/ios:native/ios:interface/ios:TwoGigabitEthernet" {
    uses config-interface-service-policy-grouping;
  }

  augment "/ios:native/ios:interface/ios:HundredGigE" {
    uses config-interface-service-policy-grouping;
  }

  augment "/ios:native/ios:interface/ios:Port-channel" {
    uses config-interface-service-policy-grouping;
  }

  augment "/ios:native/ios:interface/ios:Loopback" {
    uses config-interface-service-policy-grouping;
  }

  augment "/ios:native/ios:interface/ios:Tunnel" {
    uses config-interface-service-policy-grouping;
  }

  augment "/ios:native/ios:interface/ios:LISP" {
    uses config-interface-service-policy-grouping;
  }

  augment "/ios:native/ios:interface/ios:VirtualPortGroup" {
    uses config-interface-service-policy-grouping;
  }

  augment "/ios:native/ios:interface/ios:Virtual-Template" {
    uses config-interface-service-policy-grouping;
  }

  augment "/ios:native/ios:interface/ios:vasileft" {
    uses config-interface-service-policy-grouping;
  }

  augment "/ios:native/ios:interface/ios:vasiright" {
    uses config-interface-service-policy-grouping;
  }

  augment "/ios:native/ios:interface/ios:Vlan" {
    uses config-interface-service-policy-grouping;
  }

  augment "/ios:native/ios:interface/ios:BDI" {
    uses config-interface-service-policy-grouping;
  }
}//module
