module cisco-xe-openconfig-system-ext{

  yang-version "1";

  // namespace
  namespace "http://cisco.com/ns/yang/cisco-xe-openconfig-system-ext";

  prefix "oc-system-cisco";

  import openconfig-system { prefix oc-sys; }


  // import some basic types
  import openconfig-extensions { prefix oc-ext; }
  import tailf-common { prefix tailf; }


  // meta
  organization "Cisco";

  contact
    "www.cisco.com";

  description
    "Cisco augmentation to oc-system model.";

  oc-ext:openconfig-version "1.0.2";

  revision "2017-11-16" {
    description
      "Added support for end user license agreement";
  }
  revision "2017-10-19" {
    description
      "Added support ntp source interface configuration and config state";
  }

  augment "/oc-sys:system/oc-sys:ntp/oc-sys:config" {
           leaf ntp-source-interface {
 	     type string;
               description
                "ntp-source-interface and reference the open-config-interface";
           }
  }
  augment "/oc-sys:system/oc-sys:ntp/oc-sys:state" {
           leaf ntp-source-interface {
             type string;
               description
                "ntp-source-interface to use on outgoing NTP packets None";
           }
  }
  augment "/oc-sys:system/oc-sys:state" {
    container license {
      leaf eula {
        type string;
        description
          "The end user license agreement text";
      }
    }
  }
}
