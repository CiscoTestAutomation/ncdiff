module cisco-dmi-aaa {

  namespace "http://cisco.com/yang/cisco-dmi-aaa";

  prefix cisco-dmi-aaa;

  import cisco-self-mgmt {
    prefix cisco-sfm;
  }

  organization "Cisco Systems";

  contact "<mailto:cs-yang@cisco.com>";

  description
    "This module defines Authentication, Authorization, and
     Accounting (AAA) configuration for data model interfaces.

     Copyright (c) 2017 by Cisco Systems, Inc.
     All rights reserved.";

  revision "2017-05-17" {
    description
      "Initial version";
  }

  augment "/cisco-sfm:netconf-yang" {
    description
      "Augment data model interfaces with AAA configuration.";
    container aaa {
      description
        "Authentication, Authorization, and Accounting.";
      container authentication {
        description
          "Authentication parameters.";
        leaf login-method-list {
          type string {
            length "1..31";
          }
          default "default";
          description
            "The login authentication method list name used for
             data model interfaces.";
        }
      }
      container authorization {
        description
          "Authorization parameters.";
        leaf exec-method-list {
          type string {
            length "1..31";
          }
          default "default";
          description
            "The EXEC authorization method list name used for
             data model interfaces.";
        }
      }
    }
  }

}
